FME workspace IFC-to-CityGML2.0-LOD4-PLATEAU.fmw
Title: IFC to CityGML LOD4
History: 2025-01-16,Takashi Iijima,Original Implementation,2025-01-20,Takashi Iijima,IntBuildingInstallation の役割と interiorBuildingInstallation に統一; IfcMember を処理対象から除外

Parameters:
- SourceDataset_IFC = $(FME_MF_DIR)EC_17 June_Version 1.ifc   # Source Industry Foundation Class (IFC) File(s)
- OPENING_EXTENSION_DISTANCE_V = 0.5   # Extension Distance for Vertical Opening [mm]
- OPENING_EXTENSION_DISTANCE_H = 2   # Extension Distance for Horizontal Opening [mm]
- ROUND_COORDS = Yes   # Round Coordinate Values
- IUR_SCHEMA_XSD = $(FME_MF_DIR)urbanObject.xsd   # i-UR Schema File (urbanObject.xsd)
- DestDataset_CITYGML = $(FME_MF_DIR)energy-center_v1.gml   # Destination CityGML Dataset (*.gml)
- LOG_FILE =   # Log File
- SCHEMA_LOCATION_CITYGML = http://www.opengis.net/citygml/profiles/base/2.0 http://schemas.opengis.net/citygml/profiles/base/2.0/CityGML.xsd https://www.geospatial.jp/iur/uro/3.1 https://www.geospatial.jp/iur/schemas/uro/3.1/urbanObject.xsd   # xsi:schemaLocation
- DEST_LOD = 4.2   # Destination LOD
- DEST_COORDSYS =   # Destination Coordinate System
- SRS_NAME_CITYGML =   # GML srsName
- SRS_AXIS_ORDER_CITYGML = 1,2,3   # GML SRS Axis Order
- REPROJECTION_MODE = None   # Reprojection Mode
- GRP_REPROJECTION =   # Reprojection Parameters (Set for Manual mode)
- CRS_NAME =   # CRS Name (EPSG:xxxx)
- EASTINGS =   # Eastings
- NORTHINGS =   # Northings
- ORTHOBONAL_HEIGHT =   # Orthogonal Height
- XAXIS_ABSCISSA =   # X Axis Abscissa
- XAXIS_ORDINATE =   # X Axis Ordinate
- SCALE =   # Scale

Readers:
- IFC_1: IFC from $(SourceDataset_IFC)

IfcBuilding (reader IFC_1)
    attributes: GlobalId char(22), Name string, Description string, ObjectType string, LongName string, CompositionType string, ElevationOfRefHeight real, ElevationOfTerrain real, Axis geometry, Body geometry, FootPrint geometry, ApplicableOccurrence string, ElementType string, Elevation real, ElevationWithFlooring real, InteriorOrExteriorSpace enumeration, LandTitleNumber string, OverallHeight real, OverallWidth real, Phase string, PredefinedType enumeration, RefElevation real, RefLatitude real, RefLongitude real, Tag string, ShapeType string, OperationType string, ifc_type_name string, ifc_type_object_id string, BuildingAddress.Purpose enumeration,
      BuildingAddress.Description string, BuildingAddress.UserDefinedPurpose string, BuildingAddress.InternalLocation string, BuildingAddress.AddressLines string, BuildingAddress.PostalBox string, BuildingAddress.Town string, BuildingAddress.Region string, BuildingAddress.PostalCode string, BuildingAddress.Country string, SiteAddress.AddressLines string, SiteAddress.Country string, SiteAddress.Description string, SiteAddress.InternalLocation string, SiteAddress.PostalBox string, SiteAddress.PostalCode string, SiteAddress.Purpose enumeration, SiteAddress.Region string, SiteAddress.Town string, SiteAddress.UserDefinedPurpose string
    -> FeatureTypeFilter_Main
    -> AttributeValueMapper_ElementType
FeatureTypeFilter_Main
    ATTRIBUTES = IfcSite,IfcProject,IfcBuilding,<Unfiltered>,IfcBuildingStorey,IfcTypeObject,PropertySetDefinition,QuantitySetDefinitiotion,<Blank>
    PRESERVE_FEATURE_ORDER_LOOKUP = PER_OUTPUT_PORT
    SHOW_ERROR_INDICATORS = No
    IfcProject -> ParameterFetcher
    IfcBuilding -> AttributeCreator_Building
    <UNFILTERED> -> Tester_DropHeavy
    IfcBuildingStorey -> AttributeManager_10
Note: FeatureMerger_6 : Supplier
Junction_49
    SHOW_ERROR_INDICATORS = No
    -> Junction_50
Note: AttributeKeeper_ReprojectionParams
Junction_50
    SHOW_ERROR_INDICATORS = No
    -> FeatureMerger_6 [SUPPLIER]
Note: AttributeCreator_Building : Output
Junction_4
    SHOW_ERROR_INDICATORS = No
    -> AttributeKeeper_3
AttributeKeeper_3
    CREATE_BULK_MODE_FEATURES = NO
    KEEP_ATTRS = __bldg_gml_id,fme_basename
    SHOW_ERROR_INDICATORS = No
    -> FeatureMerger_9 [SUPPLIER]
Tester_DropHeavy
    BOOL_OP = OR
    PRESERVE_FEATURE_ORDER_LOOKUP = PER_OUTPUT_PORT
    SHOW_ERROR_INDICATORS = No
    TEST_CLAUSE = TEST @Value(fme_feature_type) IN IfcMember,IfcFurnishingElement,IfcRailing,IfcStair,IfcStairFlight
    TEST_MODE = TEST
    FAILED -> Deaggregator_2
Deaggregator_2
    ATTR_CONFLICT_RES_LOOKUP = INCOMING_IF_CONFLICT
    EXPLODE_INSTANCES = Yes
    LIST_ATTR_MODE_LOOKUP = LEAN
    RECURSIVE = No
    SHOW_ERROR_INDICATORS = No
    SPLIT_COMPOSITES = No
    ATTR_ACCUM_MODE = Merge List Attributes
    ATTR_CONFLICT_RES = Use List Attribute Values
    MODE = Flatten One Level
    DEAGGREGATED -> Aggregator_11
Aggregator_11
    ACCUM_ATTRS = One
    AGGREGATE_TYPE = Homogeneous Collection (If Possible)
    GROUP_BY = ifc_unique_id
    MODE = Geometry - Assemble One Level
    SEP = ,
    SHOW_ERROR_INDICATORS = No
    ACCUM_ATTRS_NAME = Use Attributes From One Feature
    AGGREGATE -> BoundsExtractor
AttributeManager_10
    ATTR_TABLE:
      RENAME_SET_VALUE GlobalId > _storey_global_id (char(22))
      RENAME_SET_VALUE Name > _storey_name (buffer)
      RENAME_SET_VALUE Description > _storey_description (buffer)
      RENAME_SET_VALUE ObjectType > _storey_object_type (buffer)
      RENAME_SET_VALUE LongName > _storey_long_name (buffer)
      RENAME_SET_VALUE Tag > _storey_tag (buffer)
      RENAME_SET_VALUE Elevation > _storey_elevation (real64) = @Evaluate(@CurrentAttribute()*0.001)
      RENAME_SET_VALUE ifc_unique_id > _storey_id (buffer)
      REMOVE ifc_parent_unique_id (buffer)
      REMOVE ElementType (buffer)
      REMOVE PredefinedType (buffer)
      REMOVE ShapeType (buffer)
      REMOVE OperationType (buffer)
      REMOVE ElevationWithFlooring (real64)
      REMOVE BuildingAddress.AddressLines (buffer)
      REMOVE BuildingAddress.Town (buffer)
      REMOVE BuildingAddress.Region (buffer)
      REMOVE BuildingAddress.Country (buffer)
      REMOVE SiteAddress.AddressLines (buffer)
      REMOVE SiteAddress.Country (buffer)
      REMOVE SiteAddress.Region (buffer)
      REMOVE SiteAddress.Town (buffer)
    SHOW_ERROR_INDICATORS = No
    -> FeatureMerger_9 [REQUESTOR]
    -> Junction
Tester_13
    BOOL_OP = OR
    PRESERVE_FEATURE_ORDER_LOOKUP = PER_OUTPUT_PORT
    SHOW_ERROR_INDICATORS = No
    TEST_CLAUSE = TEST $(ROUND_COORDS) = Yes
    TEST_MODE = TEST
    PASSED -> CoordinateRounder
    FAILED -> BrepSolidReplacer
Note: 誤差吸収のため、座標値の小数部桁数丸め
Note: ジオメトリの座標値の単位は mm であるものとする。 / CityGMLに出力するときは、最後のジオリファレンスのときに m に変換したうえで、degrees に座標変換する。
CoordinateRounder
    SHOW_ERROR_INDICATORS = No
    XPREC = 3
    YPREC = 3
    ZPREC = 3
    ROUNDED -> BrepSolidReplacer
NullAttributeMapper
    ATTRCHOICE_ACTION = SELECTED
    ATTRLIST = LongName Name Description ObjectType Tag
    NULL_TREATMENT_LU = EMPTY
    SHOW_ERROR_INDICATORS = No
    SOURCE_ATTR_VAL_LU = MISSINGATTR EMPTY
    ATTRCHOICE = Selected Attributes
    NULL_TREATMENT = Empty String
    SOURCE_ATTR_VAL = "Missing (Selected Attributes Only)" Empty
    -> FeatureTypeFilter_1
    -> FeatureTypeFilter_2
FeatureTypeFilter_1
    ATTRIBUTES = IfcOpeningElement,IfcDoor,IfcWindow,IfcWall,IfcWallStandardCase,IfcRoof,IfcSlab,IfcSpace,<Unfiltered>,<Blank>
    ATTRIBUTE_INFO = IfcBuilding,GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,Axis,Body,Box,FootPrint,Elevation,ElevationWithFlooring,InteriorOrExteriorSpace,LandTitleNumber,NumberOfRiser,NumberOfTreads,OverallHeight,OverallWidth,Phase,PredefinedType,RefElevation,RefLatitude,RefLongitude,RiserHeight,ShapeType,SiteAddress.AddressLines,SiteAddress.Country,SiteAddress.Description,SiteAddress.InternalLocation,SiteAddress.PostalBox,SiteAddress.PostalCode,SiteAddress.Purpose,SiteAddress.Region,SiteAddress.Town,SiteAddress.UserDefinedPurpose,Tag,TreadLength,ifc_parent_id,ifc_parent_unique_id,ifc_unique_id,fme_feature_type
    PRESERVE_FEATURE_ORDER_LOOKUP = PER_OUTPUT_PORT
    SHOW_ERROR_INDICATORS = No
    IfcOpeningElement -> AttributeManager_Opening
    IfcDoor -> AttributeManager_Opening
    IfcWindow -> Junction_86
    IfcWall -> Junction_12
    IfcWallStandardCase -> Junction_12
    IfcRoof -> Junction_12
    IfcSlab -> Junction_15
    IfcSpace -> AttributeCreator_8
Junction_86
    SHOW_ERROR_INDICATORS = No
    -> AttributeCreator_2
Junction_12
    SHOW_ERROR_INDICATORS = No
    -> AttributeCreator_3
Junction_15
    SHOW_ERROR_INDICATORS = No
    -> AttributeCreator_4
Junction_11
    SHOW_ERROR_INDICATORS = No
    -> Junction_8
Junction_8
    SHOW_ERROR_INDICATORS = No
    -> Junction_2
Note: __room_gml_id
AttributeCreator_8
    ATTR_TABLE = SET_TO __room_gml_id (varchar(200)) = room_@UUID()
    SHOW_ERROR_INDICATORS = No
    -> GeometryPartExtractor
    -> Junction_36
    -> Junction_44
    -> Junction_71
    -> Junction_46
    -> Junction_89
Note: FeatureMerger_5 : Supplier / IfcSpace の属性の復元
Junction_36
    SHOW_ERROR_INDICATORS = No
    -> Junction_37
Note: AttributeCreator_8 : Output
Junction_37
    SHOW_ERROR_INDICATORS = No
    -> FeatureMerger_5 [SUPPLIER]
Note: 個別の境界面に分解
GeometryPartExtractor
    GQUERY:
      for $geom in //geometry
      where $geom/@fme_geometry_type = 'IFMEFace'
      return number($geom/@fme_id)
    SHOW_ERROR_INDICATORS = No
    EXTRACTED -> AttributeCreator_9
Note: __int_bdry_gml_id
AttributeCreator_9
    ATTR_TABLE = SET_TO __int_bdry_gml_id (varchar(200)) = bdry_@UUID()
    SHOW_ERROR_INDICATORS = No
    -> PlanarityFilter
AttributeFilter_2
    ATTR_NAME = __orientation
    ATTR_VALUES = horizontal,vertical,<Empty>,<Missing>,<Null>,<Unfiltered>
    PRESERVE_FEATURE_ORDER_LOOKUP = PER_OUTPUT_PORT
    SHOW_ERROR_INDICATORS = No
    horizontal -> Junction_17
    vertical -> Junction_22
Junction_17
    SHOW_ERROR_INDICATORS = No
    -> Junction_6
Junction_6
    SHOW_ERROR_INDICATORS = No
    -> Tester_5
    -> Junction_67
Junction_22
    SHOW_ERROR_INDICATORS = No
    -> Junction_23
Junction_23
    SHOW_ERROR_INDICATORS = No
    -> GeometryExtractor
Note: ジオメトリを属性として保存
GeometryExtractor
    ATTR = __geometry
    KIND = fmebinary
    REMOVE_GEOMETRY = No
    SHOW_ERROR_INDICATORS = No
    KIND_LONG = FME Binary
    -> SurfaceFootprintReplacer
SurfaceFootprintReplacer
    OFFSET_Z_LOOKUP = 0
    SHADOW_TYPE = OVERHEAD
    SHOW_ERROR_INDICATORS = No
    OFFSET_Z = 0
    SHADOW_MODE = Overhead Shadow
    FOOTPRINT -> NeighborFinder [CANDIDATE]
Note: Column, Beam 等を / IntBuildingInstallation と / BuildingInstallation に分割
Junction_71
    SHOW_ERROR_INDICATORS = No
    -> Junction_72
Note: IfcSpace / 屋内空間ソリッド
Junction_72
    SHOW_ERROR_INDICATORS = No
    -> Clipper_5 [CLIPPER] [off]
Note: interiorBuildingInstallation/IntBuildingInstallation
AttributeManager_12
    ATTR_TABLE:
      SET_TO _citygml_feature_type (buffer) = IntBuildingInstallation
      SET_TO _inst_gml_id (varchar(200)) = inst_@UUID()
      SET_TO gml_parent_id (varchar(200)) = @Value(__bldg_gml_id)
      REMOVE _room___room_gml_id (varchar(200))
      REMOVE _room___bldg_gml_id (varchar(200))
      SET_TO citygml_feature_role (buffer) = interiorBuildingInstallation
      REMOVE _room_ifc_parent_unique_id (buffer)
      REMOVE _room_fme_basename (char(50))
      REMOVE _room_ifc_feature_type (buffer)
      REMOVE _room_ifc_parent_feature_type (buffer)
      REMOVE _room__storey_index (buffer)
      REMOVE _room__storey_id (buffer)
      REMOVE _room__storey_name (buffer)
      REMOVE _room_fme_feature_type (char(50))
      REMOVE _room__zmin (real64)
      REMOVE _room__zmax (real64)
      REMOVE __bldg_gml_id (varchar(200))
      REMOVE fme_feature_type (char(50))
      REMOVE _zmin (real64)
      REMOVE _zmax (real64)
      REMOVE _clipped (char(3))
      REMOVE __temp_id (int64)
    SHOW_ERROR_INDICATORS = No
    -> AttributeValueMapper
AttributeValueMapper
    LUT = IfcColumn,4.1,IfcPlate,4.2,IfcRailing,4.2,IfcRamp,4.1,IfcRampFlight,4.1,IfcStair,4.1,IfcStairFlight,4.1,IfcBeam,4.2,IfcBuildingElementProxy,4.1,IfcBuildingElementPart,4.1,IfcTransportElement,4.1
    MAPPING_DIRECTION = FORWARD
    SHOW_ERROR_INDICATORS = No
    SRC = ifc_feature_type
    VAL_ATTR = _min_lod
    -> Tester_6
Note: BuildingFurniture / CityObjectGroup
Junction_46
    SHOW_ERROR_INDICATORS = No
    -> Junction_73
Note: IfcSpace / 屋内空間ソリッド
Junction_73
    SHOW_ERROR_INDICATORS = No
    -> AttributeManager_14
    -> Junction_82
Junction_89
    SHOW_ERROR_INDICATORS = No
    -> Aggregator_9
Bufferer_3
    ANGLE = 22.5
    CAP_STYLE_LOOKUP = CAP_ARC
    CORNER_STYLE_LOOKUP = JOIN_ARC
    MODE = AREA
    OFFSET = 50
    OFFSET_UNITS = NONE
    PRECISION = APPROX
    SHOW_ERROR_INDICATORS = No
    CAP_STYLE = Arc
    CORNER_STYLE = Arc
    BUFFERED -> SpatialFilter_2 [Filter]
Note: IfcMemberは不使用とする。 / IfcMemgerは建具や階段手摺等の細かな要素に割り当てられることが多く、変換データの極端な肥大化や変換エラーにつながるリスクが高いため。
FeatureTypeFilter_2
    ATTRIBUTES = IfcWall,IfcWallStandardCase,IfcCurtainWall,IfcRoof,IfcSlab,IfcColumn,IfcBeam,IfcPlate,IfcRailing,IfcRamp,IfcRampFlight,IfcStair,IfcStairFlight,IfcBuildingElementProxy,IfcBuildingElementPart,IfcTransportElement,IfcFurnishingElement,IfcMember,<Unfiltered>,<Blank>
    ATTRIBUTE_INFO = IfcBuilding,GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,Axis,Body,Box,FootPrint,Elevation,ElevationWithFlooring,InteriorOrExteriorSpace,LandTitleNumber,NumberOfRiser,NumberOfTreads,OverallHeight,OverallWidth,Phase,PredefinedType,RefElevation,RefLatitude,RefLongitude,RiserHeight,ShapeType,SiteAddress.AddressLines,SiteAddress.Country,SiteAddress.Description,SiteAddress.InternalLocation,SiteAddress.PostalBox,SiteAddress.PostalCode,SiteAddress.Purpose,SiteAddress.Region,SiteAddress.Town,SiteAddress.UserDefinedPurpose,Tag,TreadLength,ifc_parent_id,ifc_parent_unique_id,ifc_unique_id,fme_feature_type
    PRESERVE_FEATURE_ORDER_LOOKUP = PER_OUTPUT_PORT
    SHOW_ERROR_INDICATORS = No
    IfcWall -> Junction_40
    IfcWallStandardCase -> Junction_40
    IfcCurtainWall -> Junction_40
    IfcRoof -> Junction_16
    IfcSlab -> Junction_16
    IfcColumn -> Junction_70
    IfcBeam -> Junction_70
    IfcPlate -> Junction_70
    IfcRailing -> Junction_70
    IfcRamp -> Junction_70
    IfcRampFlight -> Junction_70
    IfcStair -> Junction_70
    IfcStairFlight -> Junction_70
    IfcBuildingElementProxy -> Junction_70
    IfcBuildingElementPart -> Junction_70
    IfcTransportElement -> Junction_70
    IfcFurnishingElement -> Tester_11
Junction_40
    SHOW_ERROR_INDICATORS = No
    -> Junction_9
Note: IfcWall / IfcWallStandardCase / IfcCurtainWall
Junction_9
    SHOW_ERROR_INDICATORS = No
    -> GeometryPartExtractor_7
    -> Junction_44
Junction_44
    SHOW_ERROR_INDICATORS = No
    -> Aggregator_5
Note: Roof の下面 / Slab の上面, 最下階以外の下面
Junction_38
    SHOW_ERROR_INDICATORS = No
    -> Junction_39
Junction_39
    SHOW_ERROR_INDICATORS = No
    -> 3DForcer
Clipper_2
    ADD_NODATA = YES
    BOUNDARY_CASES = INSIDE
    CLEANING_TOLERANCE_LOOKUP = AUTO
    CLIPPED_ATTR = _clipped
    CLIPPERS_FIRST = NO
    GENERATE_LIST = NO
    GROUP_BY = _storey_index fme_basename
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    SHOW_ERROR_INDICATORS = No
    Z_VAL_SOURCE = CANDIDATE
    CLEANING_TOLERANCE = Automatic
    MISSING_M_MODE = Linear Interpolation
    MISSING_Z_MODE = Planar Interpolation
    OUTSIDE -> AttributeFilter_8
ExpressionEvaluator
    ATTRCHOICE_ACTION = SELECTED
    ATTRLIST = _storey_index
    EXPRESSION = @CurrentAttribute()+1
    SHOW_ERROR_INDICATORS = No
    ACTION = Overwrite Existing Attributes
    -> Clipper_3 [CLIPPER] [off]
Clipper_3
    ADD_NODATA = YES
    BOUNDARY_CASES = INSIDE
    CLEANING_TOLERANCE_LOOKUP = AUTO
    CLIPPED_ATTR = _clipped
    CLIPPERS_FIRST = NO
    GENERATE_LIST = NO
    GROUP_BY = _storey_index fme_basename
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    SHOW_ERROR_INDICATORS = No
    Z_VAL_SOURCE = CANDIDATE
    CLEANING_TOLERANCE = Automatic
    MISSING_M_MODE = Linear Interpolation
    MISSING_Z_MODE = Planar Interpolation
    OUTSIDE -> AttributeManager_OuterCeilingSurface
Note: Roof, Slab の側面
Junction_63
    SHOW_ERROR_INDICATORS = No
    -> Junction_64
Junction_64
    SHOW_ERROR_INDICATORS = No
    -> Bufferer_4
Clipper_4
    ADD_NODATA = YES
    BOUNDARY_CASES = INSIDE
    CLEANING_TOLERANCE_LOOKUP = AUTO
    CLIPPED_ATTR = _clipped
    CLIPPERS_FIRST = NO
    GENERATE_LIST = NO
    GROUP_BY = _storey_index fme_basename
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    SHOW_ERROR_INDICATORS = No
    Z_VAL_SOURCE = CANDIDATE
    CLEANING_TOLERANCE = Automatic
    MISSING_M_MODE = Linear Interpolation
    MISSING_Z_MODE = Planar Interpolation
    OUTSIDE -> Junction_60
GeometryPartExtractor_7
    GQUERY:
      for $geom in //geometry
      where $geom/@fme_geometry_type = 'IFMEFace'
      return number($geom/@fme_id)
    SHOW_ERROR_INDICATORS = No
    EXTRACTED -> PlanarityFilter_6
PlanarityFilter_6
    ANGULAR_TOLERANCE = 20
    ANGULAR_TOLERANCE_CHOICE_LOOKUP = CUSTOM
    OUTPUT_LOOKUP = EXPOSE_SURFACE_NORMAL
    SHOW_ERROR_INDICATORS = No
    THICKNESS_TOLERANCE = 30
    THICKNESS_TOLERANCE_CHOICE_LOOKUP = CUSTOM
    ANGULAR_TOLERANCE_CHOICE = Custom
    OUTPUT_NORMAL = Yes
    THICKNESS_TOLERANCE_CHOICE = Custom
    PLANAR -> AttributeCreator_13
Note: __bdry_gml_id
AttributeCreator_13
    ATTR_TABLE:
      SET_TO __bdry_gml_id (varchar(200)) = bdry_@UUID()
      SET_TO __rounded_normal_x (varchar(200)) = @Evaluate(@abs(@round(@Value(_surfaceNormalX)*100)))
      SET_TO __rounded_normal_y (varchar(200)) = @Evaluate(@abs(@round(@Value(_surfaceNormalY)*100)))
    SHOW_ERROR_INDICATORS = No
    -> Tester_9
Tester_9
    BOOL_OP = OR
    PRESERVE_FEATURE_ORDER_LOOKUP = PER_OUTPUT_PORT
    SHOW_ERROR_INDICATORS = No
    TEST_CLAUSE = TEST @Evaluate(@abs(@Value(_surfaceNormalZ))) < 0.1
    TEST_MODE = TEST
    PASSED -> AttributeManager_15
AttributeManager_15
    ATTR_TABLE:
      REMOVE fme_feature_type (char(50))
      REMOVE _surfaceNormalX (real64)
      REMOVE _surfaceNormalY (real64)
      REMOVE _surfaceNormalZ (real64)
      REMOVE _pointOnSurfaceX (real64)
      REMOVE _pointOnSurfaceY (real64)
      REMOVE _pointOnSurfaceZ (real64)
    SHOW_ERROR_INDICATORS = No
    -> GeometryExtractor_2
GeometryExtractor_2
    ATTR = _geometry
    KIND = fmebinary
    REMOVE_GEOMETRY = No
    SHOW_ERROR_INDICATORS = No
    KIND_LONG = FME Binary
    -> SurfaceFootprintReplacer_2
SurfaceFootprintReplacer_2
    OFFSET_Z_LOOKUP = 0
    SHADOW_TYPE = OVERHEAD
    SHOW_ERROR_INDICATORS = No
    OFFSET_Z = 0
    SHADOW_MODE = Overhead Shadow
    FOOTPRINT -> SpatialFilter_2 [Candidate]
SpatialFilter_2
    AGGREGATE_HANDLING = Yes
    BOOL_OP = OR
    BOUNDING_BOX = NO
    CURVE_BOUNDARY_RULE = ENDPOINTS_MOD2
    GROUP_BY = _storey_index fme_basename
    MULTI_BASE = YES
    PREDATTR = _predicate
    PREDICATES = INTERSECTS
    PRESERVE_FEATURE_ORDER_LOOKUP = PER_OUTPUT_PORT
    SHOW_ERROR_INDICATORS = No
    BASE_TYPE = Multiple Filters
    CURVE_BOUNDARY_RULE_PARAM = Default Rule
    PASS_CRITERIA = Pass Against One Filter
    USE_BOUNDING_BOX = No
    FAILED -> GeometryReplacer_4
GeometryReplacer_4
    KIND = fmebinary
    REMOVE_ATTRIBUTE = Yes
    SHOW_ERROR_INDICATORS = No
    SOURCE = @Value(_geometry)
    KIND_LONG = FME Binary
    -> AttributeCopier_2
AttributeCopier_2
    ATTR_TABLE = COPY ifc_unique_id > _clip_key_id
    MISSING_INPUT_ATTRS = REMOVE
    SHOW_ERROR_INDICATORS = No
    -> AttributeCreator_14
Junction_16
    SHOW_ERROR_INDICATORS = No
    -> GeometryPartExtractor_8
Note: IfcRoof / 上面 -> RoofSurface / 下面 (屋外) -> OuterCeilingSurface (同一階の外周の外側) / 側面 (屋外) -> WallSurface / IfcSlab / 上面 (屋外) -> OuterFloorSurface (同一階の外周の外側) / 下面 (最下階) -> GroundSurface / 下面 (最下階以外の屋外) -> OuterCeilingSurface (ひとつ下の階の外周の外側) / 側面 (屋外) -> WallSurface
GeometryPartExtractor_8
    GQUERY:
      for $geom in //geometry
      where $geom/@fme_geometry_type = 'IFMEFace'
      return number($geom/@fme_id)
    SHOW_ERROR_INDICATORS = No
    EXTRACTED -> GeometryValidator_2
Note: 縮退した面を除外 / Issue to Detect : / Degenerate or Corrupt Geometries
GeometryValidator_2
    ISSUE_ATTR_NAME = _issues
    PRESETS = Custom
    REPAIR = No
    RULES = TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SHOW_ERROR_INDICATORS = No
    SUMMARY = Detailed
    PASSED -> PlanarityFilter_7
PlanarityFilter_7
    ANGULAR_TOLERANCE = 20
    ANGULAR_TOLERANCE_CHOICE_LOOKUP = CUSTOM
    OUTPUT_LOOKUP = EXPOSE_SURFACE_NORMAL
    SHOW_ERROR_INDICATORS = No
    THICKNESS_TOLERANCE = 30
    THICKNESS_TOLERANCE_CHOICE_LOOKUP = CUSTOM
    ANGULAR_TOLERANCE_CHOICE = Custom
    OUTPUT_NORMAL = Yes
    THICKNESS_TOLERANCE_CHOICE = Custom
    PLANAR -> AttributeCreator_16
Note: __bdry_gml_id
AttributeCreator_16
    ATTR_TABLE = SET_TO __bdry_gml_id (varchar(200)) = bdry_@UUID()
    SHOW_ERROR_INDICATORS = No
    -> AttributeFilter_7
AttributeFilter_7
    ATTR_NAME = ifc_feature_type
    ATTR_VALUES = IfcRoof,IfcSlab,<Empty>,<Missing>,<Null>,<Unfiltered>
    PRESERVE_FEATURE_ORDER_LOOKUP = PER_OUTPUT_PORT
    SHOW_ERROR_INDICATORS = No
    IfcRoof -> TestFilter_Roof
    IfcSlab -> TestFilter_Slab
TestFilter_Roof
    DEFAULT_VALUE = 側面
    PASSED_TEST_GROUP_OUTPUT = FIRST
    PRESERVE_FEATURE_ORDER_LOOKUP = PER_OUTPUT_PORT
    SHOW_ERROR_INDICATORS = No
    TEST_LIST = "BOOL_OP,AND,COMPOSITE_TEST,""""""1"""""",TEST_CLAUSE,TEST 0.1 < @Value(_surfaceNormalZ)",上面,"BOOL_OP,OR,COMPOSITE_TEST,""""""1"""""",TEST_CLAUSE,TEST @Value(_surfaceNormalZ) < -0.1",下面
    上面 -> Junction_59
    下面 -> Junction_61
    側面 -> Junction_56
Junction_59
    SHOW_ERROR_INDICATORS = No
    -> Junction_52
Junction_52
    SHOW_ERROR_INDICATORS = No
    -> Junction_55
Junction_55
    SHOW_ERROR_INDICATORS = No
    -> AttributeManager_RoofSurface
AttributeManager_RoofSurface
    ATTR_TABLE:
      SET_TO _citygml_feature_type (buffer) = RoofSurface
      REMOVE fme_feature_type (char(50))
      REMOVE _zmin (real64)
      REMOVE _zmax (real64)
      REMOVE _surfaceNormalX (real64)
      REMOVE _surfaceNormalY (real64)
      REMOVE _surfaceNormalZ (real64)
      REMOVE _pointOnSurfaceX (real64)
      REMOVE _pointOnSurfaceY (real64)
      REMOVE _pointOnSurfaceZ (real64)
    SHOW_ERROR_INDICATORS = No
    -> Junction_51
TestFilter_Slab
    DEFAULT_VALUE = 側面
    PASSED_TEST_GROUP_OUTPUT = FIRST
    PRESERVE_FEATURE_ORDER_LOOKUP = PER_OUTPUT_PORT
    SHOW_ERROR_INDICATORS = No
    TEST_LIST = "BOOL_OP,AND,COMPOSITE_TEST,""""""1"""""",TEST_CLAUSE,TEST 0.1 < @Value(_surfaceNormalZ)",上面,"BOOL_OP,OR,COMPOSITE_TEST,""""""1"""""",TEST_CLAUSE,TEST @Value(_surfaceNormalZ) < -0.1",下面
    上面 -> Junction_61
    下面 -> Junction_62
    側面 -> Junction_56
Junction_61
    SHOW_ERROR_INDICATORS = No
    -> AttributeFilter_8
AttributeFilter_8
    ATTR_NAME = ifc_feature_type
    ATTR_VALUES = IfcSlab,IfcRoof,<Empty>,<Missing>,<Null>,<Unfiltered>
    PRESERVE_FEATURE_ORDER_LOOKUP = PER_OUTPUT_PORT
    SHOW_ERROR_INDICATORS = No
    IfcSlab -> AttributeManager_OuterFloorSurface
    IfcRoof -> AttributeManager_OuterCeilingSurface
AttributeManager_OuterFloorSurface
    ATTR_TABLE:
      SET_TO _citygml_feature_type (buffer) = OuterFloorSurface
      REMOVE fme_feature_type (char(50))
      REMOVE _zmin (real64)
      REMOVE _zmax (real64)
      REMOVE _surfaceNormalX (real64)
      REMOVE _surfaceNormalY (real64)
      REMOVE _surfaceNormalZ (real64)
      REMOVE _pointOnSurfaceX (real64)
      REMOVE _pointOnSurfaceY (real64)
      REMOVE _pointOnSurfaceZ (real64)
      REMOVE _clipped (char(9))
    SHOW_ERROR_INDICATORS = No
    -> Junction_51
Junction_62
    SHOW_ERROR_INDICATORS = No
    -> Tester_7
Tester_7
    BOOL_OP = OR
    PRESERVE_FEATURE_ORDER_LOOKUP = PER_OUTPUT_PORT
    SHOW_ERROR_INDICATORS = No
    TEST_CLAUSE = TEST 1 < @Value(_storey_index)
    TEST_MODE = TEST
    PASSED -> AttributeManager_OuterCeilingSurface
    FAILED -> Junction_58
AttributeManager_OuterCeilingSurface
    ATTR_TABLE:
      SET_TO _citygml_feature_type (buffer) = OuterCeilingSurface
      REMOVE fme_feature_type (char(50))
      REMOVE _zmin (real64)
      REMOVE _zmax (real64)
      REMOVE _surfaceNormalX (real64)
      REMOVE _surfaceNormalY (real64)
      REMOVE _surfaceNormalZ (real64)
      REMOVE _pointOnSurfaceX (real64)
      REMOVE _pointOnSurfaceY (real64)
      REMOVE _pointOnSurfaceZ (real64)
      REMOVE _clipped (char(9))
    SHOW_ERROR_INDICATORS = No
    -> Junction_51
Junction_58
    SHOW_ERROR_INDICATORS = No
    -> AttributeManager_GroundSurface
AttributeManager_GroundSurface
    ATTR_TABLE:
      SET_TO _citygml_feature_type (buffer) = GroundSurface
      REMOVE fme_feature_type (char(50))
      REMOVE _zmin (real64)
      REMOVE _zmax (real64)
      REMOVE _surfaceNormalX (real64)
      REMOVE _surfaceNormalY (real64)
      REMOVE _surfaceNormalZ (real64)
      REMOVE _pointOnSurfaceX (real64)
      REMOVE _pointOnSurfaceY (real64)
      REMOVE _pointOnSurfaceZ (real64)
    SHOW_ERROR_INDICATORS = No
    -> Junction_51
Junction_56
    SHOW_ERROR_INDICATORS = No
    -> Junction_60
Junction_60
    SHOW_ERROR_INDICATORS = No
    -> AttributeManager_WallSurface
AttributeManager_WallSurface
    ATTR_TABLE:
      SET_TO _citygml_feature_type (buffer) = WallSurface
      REMOVE fme_feature_type (char(50))
      REMOVE _zmin (real64)
      REMOVE _zmax (real64)
      REMOVE _surfaceNormalX (real64)
      REMOVE _surfaceNormalY (real64)
      REMOVE _surfaceNormalZ (real64)
      REMOVE _pointOnSurfaceX (real64)
      REMOVE _pointOnSurfaceY (real64)
      REMOVE _pointOnSurfaceZ (real64)
    SHOW_ERROR_INDICATORS = No
    -> Junction_51
Junction_51
    SHOW_ERROR_INDICATORS = No
    -> Deaggregator
Junction_70
    SHOW_ERROR_INDICATORS = No
    -> Counter_2
Counter_2
    CNT_ATTR = __temp_id
    SCOPE = Local
    SHOW_ERROR_INDICATORS = No
    START = 0
    -> Tester_12
Note: outerBuildingInstallation/BuildingInstallation
AttributeManager_13
    ATTR_TABLE:
      SET_TO _citygml_feature_type (buffer) = BuildingInstallation
      SET_TO _inst_gml_id (varchar(200)) = inst_@UUID()
      RENAME_SET_VALUE __bldg_gml_id > gml_parent_id (varchar(200))
      SET_TO citygml_feature_role (buffer) = outerBuildingInstallation
      REMOVE fme_feature_type (char(50))
      REMOVE _zmin (real64)
      REMOVE _zmax (real64)
      REMOVE _clipped (char(9))
      REMOVE __temp_id (int64)
    SHOW_ERROR_INDICATORS = No
    -> AttributeValueMapper_2
AttributeValueMapper_2
    LUT = IfcColumn,4.0,IfcPlate,4.2,IfcRailing,4.2,IfcRamp,4.0,IfcRampFlight,4.0,IfcStair,4.0,IfcStairFlight,4.0,IfcBeam,4.2,IfcBuildingElementProxy,4.0,IfcBuildingElementPart,4.0,IfcTransportElement,4.0
    MAPPING_DIRECTION = FORWARD
    SHOW_ERROR_INDICATORS = No
    SRC = ifc_feature_type
    VAL_ATTR = _min_lod
    -> Tester_6
Note: 詳細LODに応じて抽出
Tester_6
    BOOL_OP = OR
    PRESERVE_FEATURE_ORDER_LOOKUP = PER_OUTPUT_PORT
    SHOW_ERROR_INDICATORS = No
    TEST_CLAUSE = TEST @Value(_min_lod) <= $(DEST_LOD)
    TEST_MODE = TEST
    PASSED -> GeometryPartExtractor_9
AttributeManager_Installation
    ATTR_TABLE:
      SET_TO citygml_lod_name (buffer) = lod4Geometry
      RENAME_SET_VALUE _inst_gml_id > gml_id (varchar(200))
      REMOVE _room_ifc_unique_id (buffer)
      REMOVE _room_GlobalId (char(22))
      REMOVE _room_Name (buffer)
      REMOVE _room_Description (buffer)
      REMOVE _room_ObjectType (buffer)
      REMOVE _room_LongName (buffer)
      REMOVE _room_Tag (buffer)
      REMOVE _min_lod (buffer)
    SHOW_ERROR_INDICATORS = No
    -> Junction_74
AttributeManager_Furniture
    ATTR_TABLE:
      SET_TO citygml_lod_name (buffer) = lod4Geometry
      SET_TO citygml_feature_role (buffer) = interiorFurniture
      RENAME_SET_VALUE __frn_gml_id > gml_id (varchar(200))
      RENAME_SET_VALUE __room_gml_id > gml_parent_id (varchar(200))
      SET_TO _citygml_feature_type (buffer) = BuildingFurniture
      REMOVE __bldg_gml_id (varchar(200))
      REMOVE fme_feature_type (char(50))
      REMOVE _zmin (real64)
      REMOVE _zmax (real64)
    SHOW_ERROR_INDICATORS = No
    -> Junction_74
Junction_74
    SHOW_ERROR_INDICATORS = No
    -> Junction_77
Junction_77
    SHOW_ERROR_INDICATORS = No
    -> GeometryPropertySetter_LodName
Note: __bldg_gml_id を結合
FeatureMerger_9
    ATTR_ACCUM_MODE = Merge Supplier
    ATTR_CONFLICT_RES_LOOKUP = REQUESTOR_IF_CONFLICT
    GROUP_BY = fme_basename
    IGNORE_NULLS = No
    JOIN_KEYS = 1 1 AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> Junction_80
Junction_80
    SHOW_ERROR_INDICATORS = No
    -> Junction_81
Note: XMLUpdater : Update
Junction_135
    SHOW_ERROR_INDICATORS = No
    -> Junction_79
Junction_79
    SHOW_ERROR_INDICATORS = No
    -> XMLUpdater [UPDATE]
FeatureTypeFilter_Attributes
    ATTRIBUTES = IfcProject,IfcSite,IfcBuilding,IfcSpace,IfcWallStandardCase,IfcRoof,IfcSlab,IfcColumn,IfcStair,IfcStairFlight,IfcRamp,IfcRampFlight,IfcTransportElement,IfcWindow,IfcDoor,IfcOpeningElement,<Unfiltered>,<Blank>
    ATTRIBUTE_INFO = IfcBuilding,GlobalId,Name,Description,ObjectType,LongName,CompositionType,ElevationOfRefHeight,ElevationOfTerrain,BuildingAddress.Purpose,BuildingAddress.Description,BuildingAddress.UserDefinedPurpose,BuildingAddress.InternalLocation,BuildingAddress.AddressLines,BuildingAddress.PostalBox,BuildingAddress.Town,BuildingAddress.Region,BuildingAddress.PostalCode,BuildingAddress.Country,Axis,Body,FootPrint,ApplicableOccurrence,ElementType,Elevation,ElevationWithFlooring,InteriorOrExteriorSpace,LandTitleNumber,OverallHeight,OverallWidth,Phase,PredefinedType,RefElevation,RefLatitude,RefLongitude,SiteAddress.AddressLines,SiteAddress.Country,SiteAddress.Description,SiteAddress.InternalLocation,SiteAddress.PostalBox,SiteAddress.PostalCode,SiteAddress.Purpose,SiteAddress.Region,SiteAddress.Town,SiteAddress.UserDefinedPurpose,Tag,ifc_type_name,ifc_type_object_id,ifc_unique_id,ifc_parent_unique_id,fme_basename,fme_feature_type
    PRESERVE_FEATURE_ORDER_LOOKUP = PER_OUTPUT_PORT
    SHOW_ERROR_INDICATORS = No
    IfcProject -> Junction_53
    IfcSite -> XMLTemplater_Building.IfcSite [ROOT]
    IfcBuilding -> XMLTemplater_IfcBuilding [ROOT]
    IfcSpace -> GeometryPropertyExtractor_BaseQuantities
    IfcSpace -> XMLTemplater_IfcRoom [ROOT]
    IfcWallStandardCase -> XMLTemplater_IfcWallStandardCase [ROOT]
    IfcRoof -> XMLTemplater_IfcRoof [ROOT]
    IfcSlab -> XMLTemplater_IfcBuildingElement.Slab [ROOT]
    IfcColumn -> XMLTemplater_IfcBuildingElement.Colum [ROOT]
    IfcStair -> XMLTemplater_IfcBuildingElement.Stair [ROOT]
    IfcStairFlight -> XMLTemplater_IfcBuildingElement.Stair [ROOT]
    IfcRamp -> XMLTemplater_IfcBuildingElement.Ramp [ROOT]
    IfcRampFlight -> XMLTemplater_IfcBuildingElement.Ramp [ROOT]
    IfcTransportElement -> XMLTemplater_IfcBuildingElement.Transport [ROOT]
    IfcWindow -> Junction_101
    IfcDoor -> Junction_102
    IfcOpeningElement -> Junction_100
Note: Remove ifc_unique_id
AttributeRemover
    REMOVE_ATTRS = ifc_unique_id
    SHOW_ERROR_INDICATORS = No
    -> Aggregator_10
Aggregator_10
    ACCUM_ATTRS = All
    AGGREGATE_TYPE = Homogeneous Collection (If Possible)
    MODE = Geometry - Assemble One Level
    SEP = ,
    SHOW_ERROR_INDICATORS = No
    ACCUM_ATTRS_NAME = Merge Incoming Attributes
    AGGREGATE -> GeometryRemover_3
GeometryRemover_3
    REMOVE_COORDSYS = No
    SHOW_ERROR_INDICATORS = No
    -> AttributeKeeper_4
AttributeKeeper_4
    CREATE_BULK_MODE_FEATURES = NO
    KEEP_LIST = uro_ifc_building_attribute{}
    SHOW_ERROR_INDICATORS = No
    -> Junction_92
Note: FeatureMerger_Building : Supplier
Junction_92
    SHOW_ERROR_INDICATORS = No
    -> Junction_93
XMLTemplater_IfcRoom
    OUTPUT_XML_HEADER_LOOKUP = NO
    QUERY_VALIDATE = YES
    RESULT_ATTRIBUTE = uro_ifc_room_attribute{0}
    ROOT_QUERY_EXPR:
      declare namespace uro="https://www.geospatial.jp/iur/uro/3.1";
      <uro:IfcSpace>
          <uro:globalId>{fme:get-attribute("GlobalId")}</uro:globalId>
          <uro:name>{fme:get-attribute("Name")}</uro:name>
          <uro:longName>{fme:get-attribute("LongName")}</uro:longName>
          <uro:elevationWithFlooring uom="m">{fme:get-attribute("ElevationWithFlooring")}</uro:elevationWithFlooring>
      </uro:IfcSpace>
    SHOW_ERROR_INDICATORS = No
    OUTPUT_XML_HEADER = No
    VISIBLE_QUERY_VALIDATE = Yes
    -> XMLDeepCleaner_4
XMLDeepCleaner_4
    FORMATTING_CHOICE = None
    KEEP_ROOT = Yes
    REMOVE_ALL_COMMENT = Yes
    REMOVE_XML_HEADER = no
    XML_ATTRIBUTE = @Value(uro_ifc_room_attribute{0})
    XML_OUTPUT_ATTR = uro_ifc_room_attribute{0}
    -> Junction_94
GeometryPropertyExtractor_BaseQuantities
    EXTRACTTYPE = EXTRACT_TRAITS
    GQUERY:
      for $geom in //geometry
      where $geom/@fme_geometry_name = 'BaseQuantities'
      return number($geom/@fme_id)
    PREFIX_EXTRACTED_TRAITS = Yes
    SHOW_ERROR_INDICATORS = No
    EXTRACTTYPE_PARAM = Traits
    EXTRACTED -> AttributeExposer_3
AttributeExposer_3
    ATTR_TABLE = BaseQuantities.ClearHeight,real64,BaseQuantities.FinishCeilingHeight,real64,BaseQuantities.FinishFloorHeight,real64,BaseQuantities.GlobalId,buffer,BaseQuantities.GrossCeilingArea,real64,BaseQuantities.GrossFloorArea,real64,BaseQuantities.GrossPerimeter,real64,BaseQuantities.GrossVolume,real64,BaseQuantities.GrossWallArea,real64,BaseQuantities.Height,real64,BaseQuantities.ifc_instance_name,uint64,BaseQuantities.ifc_unique_id,buffer,BaseQuantities.MethodOfMeasurement,buffer,BaseQuantities.NetCeilingArea,real64,BaseQuantities.NetFloorArea,real64,BaseQuantities.NetPerimeter,real64,BaseQuantities.NetVolume,real64,BaseQuantities.NetWallArea,real64,BaseQuantities.SpaceNetFloorAreaBOMA,real64,BaseQuantities.SpaceUsableFloorAreaBOMA,real64
    SHOW_ERROR_INDICATORS = No
    -> XMLTemplater_IfcRoom_2 [ROOT]
XMLTemplater_IfcRoom_2
    OUTPUT_XML_HEADER_LOOKUP = NO
    QUERY_VALIDATE = YES
    RESULT_ATTRIBUTE = uro_ifc_room_attribute{1}
    ROOT_QUERY_EXPR:
      declare namespace uro="https://www.geospatial.jp/iur/uro/3.1";
      <uro:IfcSpaceBaseQuantity>
          <uro:grossFloorArea uom="m2">{fme:get-attribute("BaseQuantities.GrossFloorArea")}</uro:grossFloorArea>
      </uro:IfcSpaceBaseQuantity>
    SHOW_ERROR_INDICATORS = No
    OUTPUT_XML_HEADER = No
    VISIBLE_QUERY_VALIDATE = Yes
    -> XMLDeepCleaner_9
XMLDeepCleaner_9
    FORMATTING_CHOICE = None
    KEEP_ROOT = Yes
    REMOVE_ALL_COMMENT = Yes
    REMOVE_XML_HEADER = no
    XML_ATTRIBUTE = @Value(uro_ifc_room_attribute{1})
    XML_OUTPUT_ATTR = uro_ifc_room_attribute{1}
    -> Junction_94
XMLTemplater_IfcWallStandardCase
    OUTPUT_XML_HEADER_LOOKUP = NO
    QUERY_VALIDATE = YES
    RESULT_ATTRIBUTE = uro_ifc_boundary_surface_attribute{0}
    ROOT_QUERY_EXPR:
      declare namespace uro="https://www.geospatial.jp/iur/uro/3.1";
      <uro:IfcWallStandardCase>
          <uro:globalId>{fme:get-attribute("GlobalId")}</uro:globalId>
          <uro:name>{fme:get-attribute("Name")}</uro:name>
      </uro:IfcWallStandardCase>
    SHOW_ERROR_INDICATORS = No
    OUTPUT_XML_HEADER = No
    VISIBLE_QUERY_VALIDATE = Yes
    -> XMLDeepCleaner_5
XMLTemplater_IfcRoof
    OUTPUT_XML_HEADER_LOOKUP = NO
    QUERY_VALIDATE = YES
    RESULT_ATTRIBUTE = uro_ifc_boundary_surface_attribute{0}
    ROOT_QUERY_EXPR:
      declare namespace uro="https://www.geospatial.jp/iur/uro/3.1";
      <uro:IfcRoof>
          <uro:globalId>{fme:get-attribute("GlobalId")}</uro:globalId>
          <uro:shapeType codeSpace="../../codelists/IfcBuildingElement_shapeType.xml">{fme:get-attribute("_shape_type_code")}</uro:shapeType>
      </uro:IfcRoof>
    SHOW_ERROR_INDICATORS = No
    OUTPUT_XML_HEADER = No
    VISIBLE_QUERY_VALIDATE = Yes
    -> XMLDeepCleaner_5
XMLTemplater_IfcBuildingElement.Slab
    OUTPUT_XML_HEADER_LOOKUP = NO
    QUERY_VALIDATE = YES
    RESULT_ATTRIBUTE = uro_ifc_boundary_surface_attribute{0}
    ROOT_QUERY_EXPR:
      declare namespace uro="https://www.geospatial.jp/iur/uro/3.1";
      <uro:IfcBuildingElement>
          <uro:globalId>{fme:get-attribute("GlobalId")}</uro:globalId>
          <uro:elementType codeSpace="../../codelists/IfcBuildingElement_elementType.xml">{fme:get-attribute("_element_type_code")}</uro:elementType>
          <uro:predefinedType codeSpace="../../codelists/IfcBuildingElement_predefinedType.xml">{fme:get-attribute("_predefined_type_code")}</uro:predefinedType>
      </uro:IfcBuildingElement>
    SHOW_ERROR_INDICATORS = No
    OUTPUT_XML_HEADER = No
    VISIBLE_QUERY_VALIDATE = Yes
    -> XMLDeepCleaner_5
XMLDeepCleaner_5
    FORMATTING_CHOICE = None
    KEEP_ROOT = Yes
    REMOVE_ALL_COMMENT = Yes
    REMOVE_XML_HEADER = no
    XML_ATTRIBUTE = @Value(uro_ifc_boundary_surface_attribute{0})
    XML_OUTPUT_ATTR = uro_ifc_boundary_surface_attribute{0}
    -> Junction_94
XMLTemplater_IfcBuildingElement.Colum
    OUTPUT_XML_HEADER_LOOKUP = NO
    QUERY_VALIDATE = YES
    RESULT_ATTRIBUTE = uro_ifc_building_installation_attribute{0}
    ROOT_QUERY_EXPR:
      declare namespace uro="https://www.geospatial.jp/iur/uro/3.1";
      <uro:IfcBuildingElement>
          <uro:globalId>{fme:get-attribute("GlobalId")}</uro:globalId>
          <uro:name>{fme:get-attribute("Name")}</uro:name>
          <uro:tag>{fme:get-attribute("Tag")}</uro:tag>
          <uro:elementType codeSpace="../../codelists/IfcBuildingElement_elementType.xml">{fme:get-attribute("_element_type_code")}</uro:elementType>
      </uro:IfcBuildingElement>
    SHOW_ERROR_INDICATORS = No
    OUTPUT_XML_HEADER = No
    VISIBLE_QUERY_VALIDATE = Yes
    -> XMLDeepCleaner_7
XMLTemplater_IfcBuildingElement.Stair
    OUTPUT_XML_HEADER_LOOKUP = NO
    QUERY_VALIDATE = YES
    RESULT_ATTRIBUTE = uro_ifc_building_installation_attribute{0}
    ROOT_QUERY_EXPR:
      declare namespace uro="https://www.geospatial.jp/iur/uro/3.1";
      <uro:IfcBuildingElement>
          <uro:globalId>{fme:get-attribute("GlobalId")}</uro:globalId>
          <uro:elementType codeSpace="../../codelists/IfcBuildingElement_elementType.xml">{fme:get-attribute("_element_type_code")}</uro:elementType>
          <uro:shapeType codeSpace="../../codelists/IfcBuildingElement_shapeType.xml">{fme:get-attribute("_shape_type_code")}</uro:shapeType>
      </uro:IfcBuildingElement>
    SHOW_ERROR_INDICATORS = No
    OUTPUT_XML_HEADER = No
    VISIBLE_QUERY_VALIDATE = Yes
    -> XMLDeepCleaner_7
XMLTemplater_IfcBuildingElement.Ramp
    OUTPUT_XML_HEADER_LOOKUP = NO
    QUERY_VALIDATE = YES
    RESULT_ATTRIBUTE = uro_ifc_building_installation_attribute{0}
    ROOT_QUERY_EXPR:
      declare namespace uro="https://www.geospatial.jp/iur/uro/3.1";
      <uro:IfcBuildingElement>
          <uro:globalId>{fme:get-attribute("GlobalId")}</uro:globalId>
          <uro:elementType codeSpace="../../codelists/IfcBuildingElement_elementType.xml">{fme:get-attribute("_element_type_code")}</uro:elementType>
          <uro:shapeType codeSpace="../../codelists/IfcBuildingElement_shapeType.xml">{fme:get-attribute("_shape_type_code")}</uro:shapeType>
      </uro:IfcBuildingElement>
    SHOW_ERROR_INDICATORS = No
    OUTPUT_XML_HEADER = No
    VISIBLE_QUERY_VALIDATE = Yes
    -> XMLDeepCleaner_7
XMLTemplater_IfcBuildingElement.Transport
    OUTPUT_XML_HEADER_LOOKUP = NO
    QUERY_VALIDATE = YES
    RESULT_ATTRIBUTE = uro_ifc_building_installation_attribute{0}
    ROOT_QUERY_EXPR:
      declare namespace uro="https://www.geospatial.jp/iur/uro/3.1";
      <uro:IfcBuildingElement>
          <uro:globalId>{fme:get-attribute("GlobalId")}</uro:globalId>
          <uro:elementType codeSpace="../../codelists/IfcBuildingElement_elementType.xml">{fme:get-attribute("_element_type_code")}</uro:elementType>
          <uro:operationType>{fme:get-attribute("OperationType")}</uro:operationType>
      </uro:IfcBuildingElement>
    SHOW_ERROR_INDICATORS = No
    OUTPUT_XML_HEADER = No
    VISIBLE_QUERY_VALIDATE = Yes
    -> XMLDeepCleaner_7
XMLDeepCleaner_7
    FORMATTING_CHOICE = None
    KEEP_ROOT = Yes
    REMOVE_ALL_COMMENT = Yes
    REMOVE_XML_HEADER = no
    XML_ATTRIBUTE = @Value(uro_ifc_building_installation_attribute{0})
    XML_OUTPUT_ATTR = uro_ifc_building_installation_attribute{0}
    -> Junction_94
Junction_101
    SHOW_ERROR_INDICATORS = No
    -> XMLTemplater_IfcWindow [ROOT]
    -> AttributeKeeper_5
XMLTemplater_IfcWindow
    OUTPUT_XML_HEADER_LOOKUP = NO
    QUERY_VALIDATE = YES
    RESULT_ATTRIBUTE = uro_ifc_opening_attribute{0}
    ROOT_QUERY_EXPR:
      declare namespace uro="https://www.geospatial.jp/iur/uro/3.1";
      <uro:IfcWindow>
          <uro:globalId>{fme:get-attribute("GlobalId")}</uro:globalId>
          <uro:name>{fme:get-attribute("Name")}</uro:name>
          <uro:tag>{fme:get-attribute("Tag")}</uro:tag>
      </uro:IfcWindow>
    SHOW_ERROR_INDICATORS = No
    OUTPUT_XML_HEADER = No
    VISIBLE_QUERY_VALIDATE = Yes
    -> XMLDeepCleaner_6
Junction_102
    SHOW_ERROR_INDICATORS = No
    -> XMLTemplater_IfcDoor [ROOT]
    -> AttributeKeeper_5
XMLTemplater_IfcDoor
    OUTPUT_XML_HEADER_LOOKUP = NO
    QUERY_VALIDATE = YES
    RESULT_ATTRIBUTE = uro_ifc_opening_attribute{0}
    ROOT_QUERY_EXPR:
      declare namespace uro="https://www.geospatial.jp/iur/uro/3.1";
      <uro:IfcDoor>
          <uro:globalId>{fme:get-attribute("GlobalId")}</uro:globalId>
          <uro:name>{fme:get-attribute("Name")}</uro:name>
          <uro:tag>{fme:get-attribute("Tag")}</uro:tag>
      </uro:IfcDoor>
    SHOW_ERROR_INDICATORS = No
    OUTPUT_XML_HEADER = No
    VISIBLE_QUERY_VALIDATE = Yes
    -> XMLDeepCleaner_6
XMLDeepCleaner_6
    FORMATTING_CHOICE = None
    KEEP_ROOT = Yes
    REMOVE_ALL_COMMENT = Yes
    REMOVE_XML_HEADER = no
    XML_ATTRIBUTE = @Value(uro_ifc_opening_attribute{0})
    XML_OUTPUT_ATTR = uro_ifc_opening_attribute{0}
    -> Junction_94
AttributeKeeper_5
    CREATE_BULK_MODE_FEATURES = NO
    KEEP_ATTRS = ifc_parent_unique_id,ifc_unique_id,fme_basename
    SHOW_ERROR_INDICATORS = No
    -> FeatureMerger_10 [REQUESTOR]
Junction_100
    SHOW_ERROR_INDICATORS = No
    -> AttributeManager_20
AttributeManager_20
    ATTR_TABLE:
      REMOVE ShapeType (buffer)
      REMOVE OperationType (buffer)
      REMOVE BuildingAddress.AddressLines (buffer)
      REMOVE BuildingAddress.Town (buffer)
      REMOVE BuildingAddress.Region (buffer)
      REMOVE BuildingAddress.Country (buffer)
      REMOVE SiteAddress.AddressLines (buffer)
      REMOVE SiteAddress.Country (buffer)
      REMOVE SiteAddress.Region (buffer)
      REMOVE SiteAddress.Town (buffer)
      RENAME_SET_VALUE ifc_unique_id > _key_id (buffer)
      REMOVE ifc_parent_unique_id (buffer)
      REMOVE _element_type_code (buffer)
      REMOVE _predefined_type_code (buffer)
      REMOVE _shape_type_code (buffer)
    SHOW_ERROR_INDICATORS = No
    -> FeatureMerger_10 [SUPPLIER]
FeatureMerger_10
    ATTR_ACCUM_MODE = Merge Supplier
    ATTR_CONFLICT_RES_LOOKUP = REQUESTOR_IF_CONFLICT
    IGNORE_NULLS = No
    JOIN_KEYS = @Value(ifc_parent_unique_id) @Value(_key_id) AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> XMLTemplater_IfcOpeningElement [ROOT]
XMLTemplater_IfcOpeningElement
    OUTPUT_XML_HEADER_LOOKUP = NO
    QUERY_VALIDATE = YES
    RESULT_ATTRIBUTE = uro_ifc_opening_attribute{1}
    ROOT_QUERY_EXPR:
      declare namespace uro="https://www.geospatial.jp/iur/uro/3.1";
      <uro:IfcOpeningElement>
          <uro:globalId>{fme:get-attribute("GlobalId")}</uro:globalId>
      </uro:IfcOpeningElement>
    SHOW_ERROR_INDICATORS = No
    OUTPUT_XML_HEADER = No
    VISIBLE_QUERY_VALIDATE = Yes
    -> XMLDeepCleaner_10
XMLDeepCleaner_10
    FORMATTING_CHOICE = None
    KEEP_ROOT = Yes
    REMOVE_ALL_COMMENT = Yes
    REMOVE_XML_HEADER = no
    XML_ATTRIBUTE = @Value(uro_ifc_opening_attribute{1})
    XML_OUTPUT_ATTR = uro_ifc_opening_attribute{1}
    -> Junction_94
Junction_94
    SHOW_ERROR_INDICATORS = No
    -> GeometryRemover_2
GeometryRemover_2
    REMOVE_COORDSYS = No
    SHOW_ERROR_INDICATORS = No
    -> Junction_90
Note: FeatureMerger_Others : Supplier
Junction_90
    SHOW_ERROR_INDICATORS = No
    -> Junction_91
Junction_85
    SHOW_ERROR_INDICATORS = No
    -> UniqueIdentifierGenerator
Note: __opening_id 設定
UniqueIdentifierGenerator
    SHOW_ERROR_INDICATORS = No
    UUID_ATTR = __opening_id
    UUID_FORMAT = UUID_ONLY
    -> AttributeCopier
AttributeCopier
    ATTR_TABLE = COPY ifc_parent_unique_id > __opening_parent_unique_id
    MISSING_INPUT_ATTRS = REMOVE
    SHOW_ERROR_INDICATORS = No
    -> Junction_5
Junction_5
    SHOW_ERROR_INDICATORS = No
    -> Junction_18
Note: 建具 (Door, Window) のある開口部については、OpeningElement のジオメトリを建具のジオメトリ（片面）に置き換え、それを前後に押し出したソリッドに変換する。
Junction_18
    SHOW_ERROR_INDICATORS = No
    -> FeatureMerger_2 [REQUESTOR]
Junction_84
    SHOW_ERROR_INDICATORS = No
    -> Junction_87
Junction_87
    SHOW_ERROR_INDICATORS = No
    -> Aggregator_3
Junction_32
    SHOW_ERROR_INDICATORS = No
    -> Junction_33
Junction_33
    SHOW_ERROR_INDICATORS = No
    -> AttributeCreator
Note: 建具 (Door,Window) とその他に分岐
Tester_2
    BOOL_OP = OR
    PRESERVE_FEATURE_ORDER_LOOKUP = PER_OUTPUT_PORT
    SHOW_ERROR_INDICATORS = No
    TEST_CLAUSE = TEST @Value(_citygml_feature_type) IN Door,Window
    TEST_MODE = TEST
    PASSED -> FeatureMerger_2 [SUPPLIER]
    FAILED -> Junction_27
Note: 建具のある開口部抽出 / Door, Window
FeatureMerger_2
    ATTR_ACCUM_MODE = Merge Supplier
    ATTR_CONFLICT_RES_LOOKUP = SUPPLIER_IF_CONFLICT
    CLEANING_TOLERANCE_LOOKUP = AUTO
    CONNECT_Z_MODE_LOOKUP = FIRST_WINS
    GEOM_TYPE_VAL = POLYGONS
    GROUP_BY = fme_basename
    IGNORE_NULLS = No
    JOIN_KEYS = @Value(ifc_unique_id) @Value(ifc_parent_unique_id) AUTO
    MERGE_TYPE_VAL = GEOM_AND_ATTRS
    PRESERVE_FEATURE_ORDER_LOOKUP = PER_OUTPUT_PORT
    PROCESS_DUPS = YES
    REJECT_NULL_MISSING_KEYS = No
    SHOW_ERROR_INDICATORS = No
    SUPPLIERS_FIRST = No
    ATTR_CONFLICT_RES = Use Supplier
    CLEANING_TOLERANCE = Automatic
    CONNECT_Z_MODE = First Wins
    GEOM_TYPE = Build Polygons
    MERGE_TYPE = Attributes and Geometry
    MERGED -> FaceReplacer_2
    UNMERGED_REQUESTOR -> FeatureMerger_3 [REQUESTOR]
Junction_21
    SHOW_ERROR_INDICATORS = No
    -> Junction_24
Junction_24
    SHOW_ERROR_INDICATORS = No
    -> GeometryExtractor_3
Junction_27
    SHOW_ERROR_INDICATORS = No
    -> Junction_25
Junction_25
    SHOW_ERROR_INDICATORS = No
    -> FeatureMerger_3 [SUPPLIER]
Note: 建具のない開口部抽出 / ClosureSurface
FeatureMerger_3
    ATTR_ACCUM_MODE = Merge Supplier
    ATTR_CONFLICT_RES_LOOKUP = REQUESTOR_IF_CONFLICT
    GROUP_BY = fme_basename
    IGNORE_NULLS = No
    JOIN_KEYS = @Value(ifc_parent_unique_id) @Value(ifc_unique_id) AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> GeometryPartExtractor_3
GeometryExtractor_3
    ATTR = _geometry
    KIND = fmebinary
    REMOVE_GEOMETRY = No
    SHOW_ERROR_INDICATORS = No
    KIND_LONG = FME Binary
    -> SolidDissolver
SolidDissolver
    ACCUM_INPUT_ATTRS = NONE
    DEAGGREGATE_INPUT = Yes
    DISSOLVE_COUNT_ATTR = __dissolve_count
    GROUP_BY = _storey_index __normal fme_basename
    LIST_NAME = _list
    SHOW_ERROR_INDICATORS = No
    SOLID -> Tester_3
Tester_3
    BOOL_OP = OR
    PRESERVE_FEATURE_ORDER_LOOKUP = PER_OUTPUT_PORT
    SHOW_ERROR_INDICATORS = No
    TEST_CLAUSE = TEST 1 < @Value(__dissolve_count)
    TEST_MODE = TEST
    PASSED -> Counter
    FAILED -> ListIndexer
Counter
    CNT_ATTR = __temp_opening_solid_id
    SCOPE = Local
    SHOW_ERROR_INDICATORS = No
    START = 0
    -> ListExploder_2
ListExploder_2
    ATTR_CONFLICT_RES_LOOKUP = INCOMING_IF_CONFLICT
    LIST_ATTR = _list{}
    SHOW_ERROR_INDICATORS = No
    ATTR_ACCUM_MODE = Merge List Attributes
    ATTR_CONFLICT_RES = Use List Attribute Values
    ELEMENTS -> Sorter_2
Sorter_2
    GROUP_BY = __temp_opening_solid_id
    SHOW_ERROR_INDICATORS = No
    SORT_PARM = __priority NUMERIC ASCENDING __area NUMERIC DESCENDING
    SORTED -> DuplicateFilter_3
Note: OpeningElement が重複する場合は建具 (Door, Window) の形状, 単純開口の場合は面積が大きいものを採用
DuplicateFilter_3
    INPUT_ORDERED_CHOICE_LOOKUP = NO
    KEYATTR = __temp_opening_solid_id
    PRESERVE_FEATURE_ORDER_LOOKUP = PER_OUTPUT_PORT
    SHOW_ERROR_INDICATORS = No
    INPUT_ORDERED_CHOICE = No
    UNIQUE -> GeometryReplacer_3
GeometryReplacer_3
    KIND = fmebinary
    REMOVE_ATTRIBUTE = Yes
    SHOW_ERROR_INDICATORS = No
    SOURCE = @Value(_geometry)
    KIND_LONG = FME Binary
    -> AttributeManager_8
ListIndexer
    INDEX = 0
    LIST_ATTR = _list{}
    SHOW_ERROR_INDICATORS = No
    -> AttributeManager_8
AttributeManager_8
    ATTR_TABLE:
      SET_TO __rounded_normal_x (varchar(200)) = @Evaluate(@abs(@round(@Value(__normal_x)*100)))
      SET_TO __rounded_normal_y (varchar(200)) = @Evaluate(@abs(@round(@Value(__normal_y)*100)))
      REMOVE _zmin (real64)
      REMOVE _zmax (real64)
      REMOVE __area (real64)
      REMOVE __priority (varchar(200))
      REMOVE __extension_distance (varchar(200))
      REMOVE _geometry (buffer)
      REMOVE fme_feature_type (char(50))
      REMOVE __temp_opening_solid_id (int64)
      REMOVE _list{}.GlobalId (char(22))
      REMOVE _list{}.Name (buffer)
      REMOVE _list{}.Description (buffer)
      REMOVE _list{}.ObjectType (buffer)
      REMOVE _list{}.LongName (buffer)
      REMOVE _list{}.Tag (buffer)
      REMOVE _list{}.ifc_unique_id (buffer)
      REMOVE _list{}.fme_feature_type (char(50))
      REMOVE _list{}.ifc_parent_unique_id (buffer)
      REMOVE _list{}.ifc_feature_type (buffer)
      REMOVE _list{}._storey_index (buffer)
      REMOVE _list{}._storey_id (buffer)
      REMOVE _list{}._storey_name (buffer)
      REMOVE _list{}._citygml_feature_type (buffer)
      REMOVE _list{}.__orientation (varchar(200))
      REMOVE _list{}.__normal_x (real64)
      REMOVE _list{}.__normal_y (real64)
      REMOVE _list{}.__normal_z (real64)
      REMOVE _list{}.__opening_id (char(36))
      REMOVE _list{}._zmin (real64)
      REMOVE _list{}._zmax (real64)
      REMOVE _list{}.__area (real64)
      REMOVE _list{}.__priority (varchar(200))
      REMOVE _list{}.__normal (varchar(200))
      REMOVE _list{}.__extension_distance (varchar(200))
      REMOVE _list{}._geometry (buffer)
      REMOVE __dissolve_count (uint32)
    SHOW_ERROR_INDICATORS = No
    -> AttributeKeeper_2
AttributeKeeper_2
    CREATE_BULK_MODE_FEATURES = NO
    KEEP_ATTRS = __normal,__normal_x,__normal_y,__normal_z,__opening_id,__orientation,_citygml_feature_type,_storey_id,_storey_index,_storey_name,Description,GlobalId,ifc_feature_type,ifc_parent_unique_id,ifc_unique_id,LongName,Name,ObjectType,Tag,fme_basename,__rounded_normal_x,__rounded_normal_y,__opening_parent_unique_id
    SHOW_ERROR_INDICATORS = No
    -> Junction_30
Note: AttributeFilter_3 : Input
Junction_30
    SHOW_ERROR_INDICATORS = No
    -> Junction_34
Note: AttributeKeeper_2 : Output
Junction_34
    SHOW_ERROR_INDICATORS = No
    -> AttributeFilter_3
AttributeFilter_3
    ATTR_NAME = __orientation
    ATTR_VALUES = horizontal,vertical,<Empty>,<Missing>,<Null>,<Unfiltered>
    PRESERVE_FEATURE_ORDER_LOOKUP = PER_OUTPUT_PORT
    SHOW_ERROR_INDICATORS = No
    horizontal -> Junction_2
    vertical -> Junction_48
Junction_2
    SHOW_ERROR_INDICATORS = No
    -> Clipper_interior_horizontal [CLIPPER] [off]
Junction_48
    SHOW_ERROR_INDICATORS = No
    -> Junction_19
    -> Clipper_interior_vertical [CLIPPER] [off]
    -> Junction_41
Note: 開口部ソリッド
Junction_42
    SHOW_ERROR_INDICATORS = No
    -> AttributeRenamer
AttributeRenamer
    ATTR_TABLE = RENAME_SET_DEFAULT __opening_parent_unique_id > _clip_key_id
    KEEP_RENAMED_ONLY = no
    MISSING_INPUT_ATTRS = REMOVE
    SHOW_ERROR_INDICATORS = No
    -> Clipper [CLIPPER] [off]
Note: 屋外壁の開口部穴開け / Inside (開口部で切り取られた面) には、Clipper (開口部ソリッド) に設定した _citygml_featur_type が付与される。
Clipper
    ADD_NODATA = YES
    ATTR_ACCUM_MODE = MERGE
    ATTR_CONFLICT_RES = CLIPPER
    BOUNDARY_CASES = INSIDE
    CLEANING_TOLERANCE_LOOKUP = AUTO
    CLIPPED_ATTR = _clipped
    CLIPPERS_FIRST = NO
    GENERATE_LIST = NO
    GROUP_BY = fme_basename _clip_key_id __rounded_normal_x __rounded_normal_y
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    SHOW_ERROR_INDICATORS = No
    Z_VAL_SOURCE = CANDIDATE
    CLEANING_TOLERANCE = Automatic
    MISSING_M_MODE = Linear Interpolation
    MISSING_Z_MODE = Planar Interpolation
    INSIDE -> Junction_54
    OUTSIDE -> AttributeCreator_14
Note: _citygml_feature_type = WallSurface
AttributeCreator_14
    ATTR_TABLE = SET_TO _citygml_feature_type (buffer) = WallSurface
    SHOW_ERROR_INDICATORS = No
    -> Junction_54
Junction_54
    SHOW_ERROR_INDICATORS = No
    -> Deaggregator
Deaggregator
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SHOW_ERROR_INDICATORS = No
    SPLIT_COMPOSITES = No
    ATTR_ACCUM_MODE = Merge List Attributes
    ATTR_CONFLICT_RES = Use List Attribute Values
    MODE = Flatten One Level
    DEAGGREGATED -> AttributeCreator_12
Note: gml_id = face_{uuid}
AttributeCreator_12
    ATTR_TABLE = SET_TO gml_id (varchar(200)) = face_@UUID()
    SHOW_ERROR_INDICATORS = No
    -> AttributeManager_16
    -> GeometryPropertySetter_4
GeometryPropertySetter_4
    DO_REMOVE_ATTR = *
    GQUERY:
      for $geom in //geometry
      where $geom/count(parent::geometry) = 0
      return number($geom/@fme_id)
    OVERWRITE_CHOICE_OPT = yes
    SETTYPE_PARAM = Traits From Attributes
    SHOW_ERROR_INDICATORS = No
    SRC_ATTRS = gml_id
    OVERWRITE_CHOICE = Yes
    REMOVE_ATTRIBUTE = Yes
    SET -> Aggregator_6
Aggregator_6
    ACCUM_ATTRS = One
    AGGREGATE_TYPE = Homogeneous Collection (If Possible)
    GROUP_BY = __bdry_gml_id _citygml_feature_type __opening_id
    MODE = Geometry - Assemble One Level
    SEP = ,
    SHOW_ERROR_INDICATORS = No
    ACCUM_ATTRS_NAME = Use Attributes From One Feature
    AGGREGATE -> Tester_10
Tester_10
    BOOL_OP = OR
    PRESERVE_FEATURE_ORDER_LOOKUP = PER_OUTPUT_PORT
    SHOW_ERROR_INDICATORS = No
    TEST_CLAUSE = TEST @Value(_citygml_feature_type) IN Door,Window
    TEST_MODE = TEST
    PASSED -> AttributeManager_Opening
    FAILED -> AttributeManager_Boundary
Note: Door, Window
AttributeManager_Opening
    ATTR_TABLE:
      SET_TO citygml_lod_name (buffer) = lod4MultiSurface
      SET_TO citygml_feature_role (buffer) = opening
      SET_TO gml_id (varchar(200)) = opn_@UUID()
      RENAME_SET_VALUE __bdry_gml_id > gml_parent_id (varchar(200))
      REMOVE __orientation (varchar(200))
      REMOVE __normal_x (real64)
      REMOVE __normal_y (real64)
      REMOVE __normal_z (real64)
      REMOVE __normal (varchar(200))
      REMOVE __rounded_normal_x (varchar(200))
      REMOVE __rounded_normal_y (varchar(200))
      REMOVE __opening_id (char(36))
      REMOVE __bldg_gml_id (varchar(200))
      REMOVE ifc_parent_feature_type (buffer)
      REMOVE _zmin (real64)
      REMOVE _zmax (real64)
      REMOVE _clipped (char(9))
      REMOVE _clip_key_id (buffer)
      REMOVE _part_number (uint64)
      REMOVE _geometry_name (buffer)
    SHOW_ERROR_INDICATORS = No
    -> Junction_45
Note: _Boundary (境界面) / ClosureSurface の gml_id 新規作成
AttributeManager_Boundary
    ATTR_TABLE:
      SET_TO citygml_lod_name (buffer) = lod4MultiSurface
      SET_TO citygml_feature_role (buffer) = boundedBy
      SET_TO gml_id (varchar(200)) = FME_CONDITIONAL:DEFAULT_VALUE'@Value(__bdry_gml_id)'BOOL_OP;OR;COMPOSITE_TEST;1;TEST @Value(_citygml_feature_type) = ClosureSurface'bdry_@UUID()'FME_NUM_CONDITIONS2___
      REMOVE __bdry_gml_id (varchar(200))
      RENAME_SET_VALUE __bldg_gml_id > gml_parent_id (varchar(200))
      REMOVE __orientation (varchar(200))
      REMOVE __normal_x (real64)
      REMOVE __normal_y (real64)
      REMOVE __normal_z (real64)
      REMOVE __normal (varchar(200))
      REMOVE __rounded_normal_x (varchar(200))
      REMOVE __rounded_normal_y (varchar(200))
      REMOVE __opening_id (char(36))
      REMOVE ifc_parent_feature_type (buffer)
      REMOVE _zmin (real64)
      REMOVE _zmax (real64)
      REMOVE _clipped (char(9))
      REMOVE _clip_key_id (buffer)
      REMOVE _part_number (uint64)
      REMOVE _geometry_name (buffer)
    SHOW_ERROR_INDICATORS = No
    -> Junction_45
AttributeManager_16
    ATTR_TABLE:
      RENAME_SET_VALUE gml_id > xlink_href (varchar(200)) = #@CurrentAttribute()
      REMOVE GlobalId (char(22))
      REMOVE Name (buffer)
      REMOVE Description (buffer)
      REMOVE ObjectType (buffer)
      REMOVE LongName (buffer)
      REMOVE Tag (buffer)
      REMOVE ifc_unique_id (buffer)
      REMOVE ifc_parent_unique_id (buffer)
      REMOVE ifc_feature_type (buffer)
      REMOVE _storey_index (buffer)
      REMOVE _storey_id (buffer)
      REMOVE _storey_name (buffer)
      REMOVE _citygml_feature_type (buffer)
      REMOVE __orientation (varchar(200))
      REMOVE __normal_x (real64)
      REMOVE __normal_y (real64)
      REMOVE __normal_z (real64)
      REMOVE __normal (varchar(200))
      REMOVE __rounded_normal_x (varchar(200))
      REMOVE __rounded_normal_y (varchar(200))
      REMOVE __opening_id (char(36))
      REMOVE __bdry_gml_id (varchar(200))
      REMOVE ifc_parent_feature_type (buffer)
      REMOVE _zmin (real64)
      REMOVE _zmax (real64)
      REMOVE _clipped (char(9))
      REMOVE _clip_key_id (buffer)
      REMOVE _part_number (uint64)
      REMOVE _geometry_name (buffer)
    SHOW_ERROR_INDICATORS = No
    USER_EXPOSED_ATTRIBUTES = __wall_gml_id
    -> GeometryPropertySetter_5
GeometryPropertySetter_5
    DO_REMOVE_ATTR = *
    GQUERY:
      for $geom in //geometry
      where $geom/count(parent::geometry) = 0
      return number($geom/@fme_id)
    OVERWRITE_CHOICE_OPT = yes
    SETTYPE_PARAM = Traits From Attributes
    SHOW_ERROR_INDICATORS = No
    SRC_ATTRS = xlink_href
    OVERWRITE_CHOICE = Yes
    REMOVE_ATTRIBUTE = Yes
    SET -> Aggregator_4
Aggregator_4
    ACCUM_ATTRS = One
    AGGREGATE_TYPE = Homogeneous Collection (If Possible)
    GROUP_BY = __bldg_gml_id fme_basename
    MODE = Geometry - Assemble One Level
    SEP = ,
    SHOW_ERROR_INDICATORS = No
    ACCUM_ATTRS_NAME = Use Attributes From One Feature
    AGGREGATE -> AttributeManager_Building
AttributeManager_Building
    ATTR_TABLE:
      SET_TO citygml_lod_name (buffer) = lod4MultiSurface
      SET_TO citygml_feature_role (buffer) = cityObjectMember
      RENAME_SET_VALUE __bldg_gml_id > gml_id (varchar(200))
      SET_TO _citygml_feature_type (buffer) = Building
    SHOW_ERROR_INDICATORS = No
    -> Junction_45
Junction_45
    SHOW_ERROR_INDICATORS = No
    -> GeometryPropertySetter_LodName
Note: Junction_16 : Output
Junction_20
    SHOW_ERROR_INDICATORS = No
    -> AttributeKeeper
AttributeKeeper
    CREATE_BULK_MODE_FEATURES = NO
    KEEP_ATTRS = __orientation,_storey_index,fme_basename
    SHOW_ERROR_INDICATORS = No
    -> AttributeFilter_5
AttributeFilter_5
    ATTR_NAME = __orientation
    ATTR_VALUES = horizontal,vertical,<Empty>,<Missing>,<Null>,<Unfiltered>
    PRESERVE_FEATURE_ORDER_LOOKUP = PER_OUTPUT_PORT
    SHOW_ERROR_INDICATORS = No
    vertical -> CenterPointReplacer
Note: 鉛直の開口部を中心点に変換
CenterPointReplacer
    POINTTYPE = CENTER
    SHOW_ERROR_INDICATORS = No
    POINT -> NeighborFinder [BASE]
Junction_68
    SHOW_ERROR_INDICATORS = No
    -> Tester_5
    -> Junction_67
Junction_67
    SHOW_ERROR_INDICATORS = No
    -> Junction_69
Junction_69
    SHOW_ERROR_INDICATORS = No
    -> GeometryRemover
Junction_13
    SHOW_ERROR_INDICATORS = No
    -> AttributeCreator_11
Note: __clipped = no
AttributeCreator_11
    ATTR_TABLE = SET_TO __clipped (buffer) = no
    SHOW_ERROR_INDICATORS = No
    -> Tester_5
Tester_8
    BOOL_OP = COMPOSITE
    COMPOSITE_TEST = 1 AND 2
    PRESERVE_FEATURE_ORDER_LOOKUP = PER_OUTPUT_PORT
    SHOW_ERROR_INDICATORS = No
    TEST_CLAUSE:
      TEST @Value(__clipped) = no
      TEST @Value(_citygml_feature_type) IN Door,Window
    TEST_MODE = TEST
    PASSED -> DuplicateFilter_4
    PASSED -> Junction_66
    FAILED -> Junction_66
Junction_57
    SHOW_ERROR_INDICATORS = No
    -> Junction_65
Junction_65
    SHOW_ERROR_INDICATORS = No
    -> Aggregator_2
Junction_66
    SHOW_ERROR_INDICATORS = No
    -> Junction_29
Junction_29
    SHOW_ERROR_INDICATORS = No
    -> AttributeManager_3
Junction_26
    SHOW_ERROR_INDICATORS = No
    -> AttributeManager_3
AttributeManager_3
    ATTR_TABLE:
      REMOVE __opening_id (char(36))
      REMOVE _element_index (uint32)
      REMOVE __distance (real64)
      REMOVE _match_id (uint32)
    SHOW_ERROR_INDICATORS = No
    USER_EXPOSED_ATTRIBUTES = __clipped2
    -> NullAttributeMapper_2
NullAttributeMapper_2
    ATTRCHOICE_ACTION = ALL
    NULL_TREATMENT_LU = DELETEATTR
    SHOW_ERROR_INDICATORS = No
    SOURCE_ATTR_VAL_LU = SETNULL EMPTY
    ATTRCHOICE = All Attributes
    NULL_TREATMENT = Missing
    SOURCE_ATTR_VAL = Null Empty
    -> Sorter_3
Sorter_3
    GROUP_BY = fme_basename
    SHOW_ERROR_INDICATORS = No
    SORT_PARM = __room_gml_id ALPHA ASCENDING
    SORTED -> SolidBoundaryCloser [Boundary]
Note: 水密になるようにソリッド境界ジオメトリを修正
SolidBoundaryCloser
    APPEARANCE_HANDLING_MODE = Keep
    Untouched -> Junction_7
    Repaired -> Junction_7
    Failed -> Junction_7
Junction_7
    SHOW_ERROR_INDICATORS = No
    -> GeometryPartExtractor_6
GeometryPartExtractor_6
    GQUERY:
      for $geom in //geometry
      where $geom/@fme_geometry_type = 'IFMEFace'
      return number($geom/@fme_id)
    SHOW_ERROR_INDICATORS = No
    EXTRACTED -> Orientor
    UNTOUCHED -> Orientor
Orientor
    FLIP_APPEARANCES_LOOKUP = FLIP_APPEARANCES
    KIND = REVERSE
    SHOW_ERROR_INDICATORS = No
    FLIP_APPEARANCES_CHOICE = Yes
    ORIENTED -> AttributeCreator_10
Note: gml_id = face_{uuid}
AttributeCreator_10
    ATTR_TABLE = SET_TO gml_id (varchar(200)) = face_@UUID()
    SHOW_ERROR_INDICATORS = No
    -> GeometryPropertySetter
    -> AttributeManager_9
GeometryPropertySetter
    DO_REMOVE_ATTR = *
    GQUERY:
      for $geom in //geometry
      where $geom/count(parent::geometry) = 0
      return number($geom/@fme_id)
    OVERWRITE_CHOICE_OPT = yes
    SETTYPE_PARAM = Traits From Attributes
    SHOW_ERROR_INDICATORS = No
    SRC_ATTRS = gml_id
    OVERWRITE_CHOICE = Yes
    REMOVE_ATTRIBUTE = Yes
    SET -> Aggregator_2
Aggregator_2
    ACCUM_ATTRS = One
    AGGREGATE_TYPE = Homogeneous Collection (If Possible)
    GROUP_BY = __int_bdry_gml_id _citygml_feature_type
    MODE = Geometry - Assemble One Level
    SEP = ,
    SHOW_ERROR_INDICATORS = No
    ACCUM_ATTRS_NAME = Use Attributes From One Feature
    AGGREGATE -> TestFilter
TestFilter
    DEFAULT_VALUE = Boundary
    PASSED_TEST_GROUP_OUTPUT = FIRST
    PRESERVE_FEATURE_ORDER_LOOKUP = PER_OUTPUT_PORT
    SHOW_ERROR_INDICATORS = No
    TEST_LIST = "BOOL_OP,OR,COMPOSITE_TEST,""""""1"""""",TEST_CLAUSE,TEST @Value(_citygml_feature_type) = Door",Door,"BOOL_OP,OR,COMPOSITE_TEST,""""""1"""""",TEST_CLAUSE,TEST @Value(_citygml_feature_type) = Window",Window
    Door -> AttributeManager_inDoor
    Window -> AttributeManager_inWindow
    Boundary -> AttributeManager_in_Boundary
AttributeManager_inDoor
    ATTR_TABLE:
      SET_TO citygml_lod_name (buffer) = lod4MultiSurface
      SET_TO citygml_feature_role (buffer) = opening
      SET_TO gml_id (varchar(200)) = opn_@UUID()
      RENAME_SET_VALUE __int_bdry_gml_id > gml_parent_id (varchar(200))
      REMOVE __room_gml_id (varchar(200))
      REMOVE __orientation (varchar(200))
      REMOVE __normal_x (real64)
      REMOVE __normal_y (real64)
      REMOVE __normal_z (real64)
      REMOVE __clipped (char(3))
      REMOVE _zmin (real64)
      REMOVE _zmax (real64)
      REMOVE __rounded_normal_x (varchar(200))
      REMOVE __rounded_normal_y (varchar(200))
      REMOVE __normal (varchar(200))
      REMOVE _remnant (char(3))
      REMOVE __bldg_gml_id (varchar(200))
    SHOW_ERROR_INDICATORS = No
    -> Junction_47
AttributeManager_inWindow
    ATTR_TABLE:
      SET_TO citygml_lod_name (buffer) = lod4MultiSurface
      SET_TO citygml_feature_role (buffer) = opening
      SET_TO gml_id (varchar(200)) = opn_@UUID()
      RENAME_SET_VALUE __int_bdry_gml_id > gml_parent_id (varchar(200))
      REMOVE __room_gml_id (varchar(200))
      REMOVE __orientation (varchar(200))
      REMOVE __normal_x (real64)
      REMOVE __normal_y (real64)
      REMOVE __normal_z (real64)
      REMOVE __clipped (char(3))
      REMOVE _zmin (real64)
      REMOVE _zmax (real64)
      REMOVE __rounded_normal_x (varchar(200))
      REMOVE __rounded_normal_y (varchar(200))
      REMOVE __normal (varchar(200))
      REMOVE _remnant (char(3))
      REMOVE __bldg_gml_id (varchar(200))
    SHOW_ERROR_INDICATORS = No
    -> Junction_47
AttributeManager_in_Boundary
    ATTR_TABLE:
      SET_TO citygml_lod_name (buffer) = lod4MultiSurface
      SET_TO citygml_feature_role (buffer) = boundedBy
      SET_TO gml_id (varchar(200)) = FME_CONDITIONAL:DEFAULT_VALUE'@Value(__int_bdry_gml_id)'BOOL_OP;OR;COMPOSITE_TEST;1;TEST @Value(_citygml_feature_type) = ClosureSurface'bdry_@UUID()'FME_NUM_CONDITIONS2___
      REMOVE __int_bdry_gml_id (varchar(200))
      RENAME_SET_VALUE __room_gml_id > gml_parent_id (varchar(200))
      REMOVE __orientation (varchar(200))
      REMOVE __normal_x (real64)
      REMOVE __normal_y (real64)
      REMOVE __normal_z (real64)
      REMOVE __clipped (char(3))
      REMOVE _zmin (real64)
      REMOVE _zmax (real64)
      REMOVE __rounded_normal_x (varchar(200))
      REMOVE __rounded_normal_y (varchar(200))
      REMOVE __normal (varchar(200))
      REMOVE _remnant (char(3))
      REMOVE __bldg_gml_id (varchar(200))
    SHOW_ERROR_INDICATORS = No
    -> Junction_47
Note: xlink_href = #@Value(gml_id) / gml_geometry_reversed = Yes
AttributeManager_9
    ATTR_TABLE:
      SET_TO xlink_href (varchar(200)) = #@Value(gml_id)
      SET_TO gml_geometry_reversed (buffer) = Yes
      REMOVE gml_id (varchar(200))
      REMOVE GlobalId (char(22))
      REMOVE Name (buffer)
      REMOVE Description (buffer)
      REMOVE ObjectType (buffer)
      REMOVE LongName (buffer)
      REMOVE Tag (buffer)
      REMOVE ifc_unique_id (buffer)
      REMOVE ifc_parent_unique_id (buffer)
      REMOVE ifc_feature_type (buffer)
      REMOVE ifc_parent_feature_type (buffer)
      REMOVE _citygml_feature_type (buffer)
      REMOVE _storey_index (buffer)
      REMOVE _storey_id (buffer)
      REMOVE _storey_name (buffer)
      REMOVE __orientation (varchar(200))
      REMOVE __normal_x (real64)
      REMOVE __normal_y (real64)
      REMOVE __normal_z (real64)
      REMOVE __clipped (char(3))
      REMOVE _zmin (real64)
      REMOVE _zmax (real64)
      REMOVE __rounded_normal_x (varchar(200))
      REMOVE __rounded_normal_y (varchar(200))
      REMOVE __normal (varchar(200))
      REMOVE __int_bdry_gml_id (varchar(200))
      REMOVE _remnant (char(3))
    SHOW_ERROR_INDICATORS = No
    -> GeometryPropertySetter_2
GeometryPropertySetter_2
    DO_REMOVE_ATTR = *
    GQUERY:
      for $geom in //geometry
      where $geom/count(parent::geometry) = 0
      return number($geom/@fme_id)
    OVERWRITE_CHOICE_OPT = yes
    SETTYPE_PARAM = Traits From Attributes
    SHOW_ERROR_INDICATORS = No
    SRC_ATTRS = xlink_href gml_geometry_reversed
    OVERWRITE_CHOICE = Yes
    REMOVE_ATTRIBUTE = Yes
    SET -> Sorter_4
Sorter_4
    GROUP_BY = fme_basename
    SHOW_ERROR_INDICATORS = No
    SORT_PARM = __room_gml_id ALPHA ASCENDING
    SORTED -> Aggregator
Aggregator
    ACCUM_ATTRS = None
    AGGREGATE_TYPE = Homogeneous Collection (If Possible)
    GROUP_BY = __room_gml_id fme_basename
    MODE = Geometry - Assemble One Level
    SEP = ,
    SHOW_ERROR_INDICATORS = No
    ACCUM_ATTRS_NAME = Drop Incoming Attributes
    AGGREGATE -> GeometryCoercer
GeometryCoercer
    GQUERY:
      for $geom in //geometry
      where $geom/count(parent::geometry) = 0
      return number($geom/@fme_id)
    KIND = fme_brep_solid
    SHOW_ERROR_INDICATORS = No
    COERCED -> FeatureMerger_5 [REQUESTOR]
Note: IfcSpaceの属性の復元
FeatureMerger_5
    ATTR_ACCUM_MODE = Merge Supplier
    ATTR_CONFLICT_RES_LOOKUP = SUPPLIER_IF_CONFLICT
    GROUP_BY = fme_basename
    IGNORE_NULLS = No
    JOIN_KEYS = @Value(__room_gml_id) @Value(__room_gml_id) AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Supplier
    MERGE_TYPE = Attributes Only
    MERGED -> AttributeManager_Room
AttributeManager_Room
    ATTR_TABLE:
      SET_TO citygml_lod_name (buffer) = lod4Solid
      SET_TO citygml_feature_role (buffer) = interiorRoom
      RENAME_SET_VALUE __room_gml_id > gml_id (varchar(200))
      RENAME_SET_VALUE __bldg_gml_id > gml_parent_id (varchar(200))
      SET_TO _citygml_feature_type (buffer) = Room
      REMOVE fme_feature_type (char(50))
      REMOVE _zmin (real64)
      REMOVE _zmax (real64)
    SHOW_ERROR_INDICATORS = No
    -> Junction_47
Junction_47
    SHOW_ERROR_INDICATORS = No
    -> Junction_76
Note: GeometryPropertySetter_LodName
Junction_76
    SHOW_ERROR_INDICATORS = No
    -> Junction_78
Note: Junction_47 : Output
Junction_78
    SHOW_ERROR_INDICATORS = No
    -> GeometryPropertySetter_LodName
Note: citygml_lod_name プロパティ設定
GeometryPropertySetter_LodName
    DO_REMOVE_ATTR = *
    GQUERY:
      for $geom in //geometry
      where $geom/count(parent::geometry) = 0
      return number($geom/@fme_id)
    OVERWRITE_CHOICE_OPT = yes
    SETTYPE_PARAM = Traits From Attributes
    SHOW_ERROR_INDICATORS = No
    SRC_ATTRS = citygml_lod_name
    OVERWRITE_CHOICE = Yes
    REMOVE_ATTRIBUTE = Yes
    SET -> FeatureMerger_6 [REQUESTOR]
Junction_98
    SHOW_ERROR_INDICATORS = No
    -> Junction_99
Junction_99
    SHOW_ERROR_INDICATORS = No
    -> FeatureWriter_CityGML [Set]
Junction_95
    SHOW_ERROR_INDICATORS = No
    -> Junction_97
Junction_97
    SHOW_ERROR_INDICATORS = No
    -> Junction_96
Junction_96
    SHOW_ERROR_INDICATORS = No
    -> FeatureWriter_CityGML [Set]
FeatureWriter_CityGML
    CITYGML_ADD_NAMESPACE_PREFIX_TO_FEATURE_TYPES = Yes
    CITYGML_ADE = Other
    CITYGML_ADE_XSD_DOC = $(IUR_SCHEMA_XSD)
    CITYGML_CITYGML_VALIDATION = No
    CITYGML_COORDINATE_SYSTEM_GRANULARITY = DATASET
    CITYGML_DESTINATION_DATASETTYPE_VALIDATION = Yes
    CITYGML_DOCUMENT_ENCODING = utf-8
    CITYGML_INDENT_SIZE = 1
    CITYGML_MAX_ATTRIBUTES_PER_NESTED_ATTRIBUTE = 1
    CITYGML_PRETTY_PRINT = Yes
    CITYGML_REMOVE_AUTO_GENERATED_IDS_WHEN_POSSIBLE = Yes
    CITYGML_REPLACE_TABS_WITH_SPACES = No
    CITYGML_RESTRICT_CURVES_TO_POLYLINES = Yes
    CITYGML_SCHEMA_LOCATION = $(SCHEMA_LOCATION_CITYGML)
    CITYGML_SRS_AXIS_ORDER = $(SRS_AXIS_ORDER_CITYGML)
    CITYGML_SRS_NAME = $(SRS_NAME_CITYGML)
    CITYGML_TEXTURE_OUTPUT_FORMAT = NONE
    CITYGML_THEME_NAME = FMETheme
    CITYGML_USE_CITYGML_SCHEMA_FILES = Yes
    CITYGML_USE_COORDINATE_PRECISION = NO
    CITYGML_USE_CORE_NAMESPACE_PREFIX = Yes
    CITYGML_USE_XLINK_HREF_GEOMETRY_TRAITS = Yes
    CITYGML_VERSION = 2.0
    CONFIG_PARAMETERS = ESCAPE_COMMAS_IN_FTP_FORMAT_PARAMETERS,no
    DATASET = $(DestDataset_CITYGML)
    DATASET_ATTR = _dataset
    FEATURE_TYPE_LIST_ATTR = _feature_types
    FORMAT = CITYGML
    GROUP_BY = fme_basename
    MORE_SUMMARY_ATTRS = fme_basename
    SHOW_ERROR_INDICATORS = No
    TOTAL_FEATURES_WRITTEN_ATTR = _total_features_written
    SUMMARY -> AttributeManager_18
AttributeManager_18
    ATTR_TABLE:
      SET_TO fme_basename (varchar(200)) = @Value(_feature_types{0}.fme_basename)
      REMOVE _feature_types{}.count (uint64)
      REMOVE _feature_types{}.name (buffer)
      REMOVE _feature_types{}.fme_basename (buffer)
      REMOVE _total_features_written (uint64)
    SHOW_ERROR_INDICATORS = No
    -> XMLUpdater [DOCUMENT]

Bookmark: 投影変換パラメーター取得
ParameterFetcher
    ATTR_LIST = ProjectedCRS.Name $(CRS_NAME) MapConversion.Eastings $(EASTINGS) MapConversion.Northings $(NORTHINGS) MapConversion.OrthogonalHeight $(ORTHOBONAL_HEIGHT) MapConversion.XAxisAbscissa $(XAXIS_ABSCISSA) MapConversion.XAxisOrdinate $(XAXIS_ORDINATE) MapConversion.Scale $(SCALE) _reprojection_mode $(REPROJECTION_MODE)
    SHOW_ERROR_INDICATORS = No
    -> AttributeFilter_ReprojectionMode
Note: Reprojection Mode / Manual / Auto / None (座標系変換・設定なし)
AttributeFilter_ReprojectionMode
    ATTR_NAME = _reprojection_mode
    ATTR_VALUES = Manual,Auto,None,<Empty>,<Missing>,<Null>,<Unfiltered>
    PRESERVE_FEATURE_ORDER_LOOKUP = PER_OUTPUT_PORT
    SHOW_ERROR_INDICATORS = No
    Manual -> JSONTemplater_2 [ROOT]
    Auto -> GeometryPropertyExtractor
    None -> Junction_28
JSONTemplater_2
    QUERY_VALIDATE = YES
    RESULT_ATTRIBUTE = _reprojection_params
    ROOT_QUERY_EXPR:
      {
          "ProjectedCRS" : {
              "Name" : fme:get-attribute("ProjectedCRS.Name")
          },
          "MapConversion" : {
              "Eastings" : xs:double(fme:get-attribute("MapConversion.Eastings")),
              "Northings" : xs:double(fme:get-attribute("MapConversion.Northings")),
              "OrthogonalHeight" : xs:double(fme:get-attribute("MapConversion.OrthogonalHeight")),
              "XAxisAbscissa" : xs:double(fme:get-attribute("MapConversion.XAxisAbscissa")),
              "XAxisOrdinate" : xs:double(fme:get-attribute("MapConversion.XAxisOrdinate")),
              "Scale" : xs:double(fme:get-attribute("MapConversion.Scale"))
          }
      }
    SHOW_ERROR_INDICATORS = No
    VISIBLE_QUERY_VALIDATE = Yes
    -> Junction_88
Junction_88
    SHOW_ERROR_INDICATORS = No
    -> AttributeKeeper_ReprojectionParams
GeometryPropertyExtractor
    EXTRACTTYPE = EXTRACT_TRAITS
    GQUERY:
      for $geom in //geometry
      where $geom/count(parent::geometry) = 0
      return number($geom/@fme_id)
    PREFIX_EXTRACTED_TRAITS = Yes
    SHOW_ERROR_INDICATORS = No
    EXTRACTTYPE_PARAM = Traits
    EXTRACTED -> AttributeExposer
AttributeExposer
    ATTR_TABLE = ePSet_ProjectedCRS.Name,,ePSet_ProjectedCRS.Description,,ePSet_ProjectedCRS.GeodeticDatum,,ePSet_ProjectedCRS.VerticalDatum,,ePSet_ProjectedCRS.MapProjection,,ePSet_ProjectedCRS.MapZone,,ePSet_MapConversion.Eastings,,ePSet_MapConversion.Northings,,ePSet_MapConversion.OrthogonalHeight,,ePSet_MapConversion.XAxisAbscissa,,ePSet_MapConversion.XAxisOrdinate,,ePSet_MapConversion.Scale,
    SHOW_ERROR_INDICATORS = No
    -> JSONTemplater_3 [ROOT]
JSONTemplater_3
    QUERY_VALIDATE = YES
    RESULT_ATTRIBUTE = _reprojection_params
    ROOT_QUERY_EXPR:
      {
          "ProjectedCRS" : {
              "Name" : fme:get-attribute("ePSet_ProjectedCRS.Name"),
              "Description" : fme:get-attribute("ePSet_ProjectedCRS.Description"),
              "GeodeticDatum" : fme:get-attribute("ePSet_ProjectedCRS.GeodeticDatum"),
              "VerticalDatum" : fme:get-attribute("ePSet_ProjectedCRS.VerticalDatum"),
              "MapProjection" : fme:get-attribute("ePSet_ProjectedCRS.MapProjection"),
              "MapZone" : fme:get-attribute("ePSet_ProjectedCRS.MapZone")
          },
          "MapConversion" : {
              "Eastings" : xs:double(fme:get-attribute("ePSet_MapConversion.Eastings")),
              "Northings" : xs:double(fme:get-attribute("ePSet_MapConversion.Northings")),
              "OrthogonalHeight" : xs:double(fme:get-attribute("ePSet_MapConversion.OrthogonalHeight")),
              "XAxisAbscissa" : xs:double(fme:get-attribute("ePSet_MapConversion.XAxisAbscissa")),
              "XAxisOrdinate" : xs:double(fme:get-attribute("ePSet_MapConversion.XAxisOrdinate")),
              "Scale" : xs:double(fme:get-attribute("ePSet_MapConversion.Scale"))
          }
      }
    SHOW_ERROR_INDICATORS = No
    VISIBLE_QUERY_VALIDATE = Yes
    -> AttributeKeeper_ReprojectionParams
Junction_28
    SHOW_ERROR_INDICATORS = No
    -> Junction_35
Junction_35
    SHOW_ERROR_INDICATORS = No
    -> AttributeKeeper_ReprojectionParams
AttributeKeeper_ReprojectionParams
    CREATE_BULK_MODE_FEATURES = NO
    KEEP_ATTRS = _reprojection_params,fme_basename
    SHOW_ERROR_INDICATORS = No
    -> Junction_49

Bookmark: 所属先 Storey の情報 (storey_index,, storey_id, storey_name,) を全てのフィーチャーに付与
Note: __bldg_gml_id
AttributeCreator_Building
    ATTR_TABLE:
      SET_TO __bldg_gml_id (varchar(200)) = bldg_@UUID()
      SET_TO _citygml_feature_type (buffer) = Building
    SHOW_ERROR_INDICATORS = No
    -> JSONTemplater [ROOT]
    -> Junction_3
Note: AttributeKeeper_3 : Input
Junction_3
    SHOW_ERROR_INDICATORS = No
    -> Junction_4
BoundsExtractor
    SHOW_ERROR_INDICATORS = No
    ZMAX = _zmax
    ZMIN = _zmin
    -> JSONTemplater [ELEMENTS_3]
    -> AttributeManager_17
    -> JSONTemplater [ELEMENTS_2]
    -> JSONTemplater [ELEMENTS]
AttributeManager_17
    ATTR_TABLE:
      REMOVE Elevation (real64)
      REMOVE ElementType (buffer)
      REMOVE ElevationWithFlooring (real64)
      REMOVE PredefinedType (buffer)
      REMOVE ShapeType (buffer)
      REMOVE OperationType (buffer)
      REMOVE BuildingAddress.AddressLines (buffer)
      REMOVE BuildingAddress.Town (buffer)
      REMOVE BuildingAddress.Region (buffer)
      REMOVE BuildingAddress.Country (buffer)
      REMOVE SiteAddress.AddressLines (buffer)
      REMOVE SiteAddress.Country (buffer)
      REMOVE SiteAddress.Region (buffer)
      REMOVE SiteAddress.Town (buffer)
    SHOW_ERROR_INDICATORS = No
    -> FeatureMerger [SUPPLIER]
Junction
    SHOW_ERROR_INDICATORS = No
    -> JSONTemplater [STOREY]
JSONTemplater
    CONSECUTIVE_GROUP_LOOKUP = YES
    ELEMENTS_2_QUERY_EXPR:
      {
          "name" : fme:get-attribute("Name"),
          "ifc_feature_type" : fme:get-attribute("fme_feature_type"),
          "ifc_unique_id" : fme:get-attribute("ifc_unique_id"),
          "zmin" : xs:double(fme:get-attribute("_zmin")),
          "zmax" : xs:double(fme:get-attribute("_zmax")),
          "elements" : [
              fme:process-features("ELEMENTS_3",
                  "ifc_parent_unique_id",
                  fme:get-attribute("ifc_unique_id"))
          ]
      }
    ELEMENTS_3_QUERY_EXPR:
      {
          "name" : fme:get-attribute("Name"),
          "ifc_feature_type" : fme:get-attribute("fme_feature_type"),
          "ifc_unique_id" : fme:get-attribute("ifc_unique_id"),
          "zmin" : xs:double(fme:get-attribute("_zmin")),
          "zmax" : xs:double(fme:get-attribute("_zmax")),
          "elements" : []
      }
    ELEMENTS_QUERY_EXPR:
      {
          "name" : fme:get-attribute("Name"),
          "ifc_feature_type" : fme:get-attribute("fme_feature_type"),
          "ifc_unique_id" : fme:get-attribute("ifc_unique_id"),
          "zmin" : xs:double(fme:get-attribute("_zmin")),
          "zmax" : xs:double(fme:get-attribute("_zmax")),
          "elements" : [
              fme:process-features("ELEMENTS_2",
                  "ifc_parent_unique_id",
                  fme:get-attribute("ifc_unique_id"))
          ]
      }
    GROUP_BY = fme_basename
    QUERY_VALIDATE = YES
    RESULT_ATTRIBUTE = _hierarchy
    ROOT_QUERY_EXPR = [ fme:process-features("STOREY") ]
    SHOW_ERROR_INDICATORS = No
    STOREY_QUERY_EXPR:
      {
          "name" : fme:get-attribute("_storey_name"),
          "ifc_feature_type" : fme:get-attribute("fme_feature_type"),
          "ifc_unique_id" : fme:get-attribute("_storey_id"),
          "elevation" : fme:get-attribute("_storey_elevation"),
          "elements" : [
              fme:process-features("ELEMENTS",
                  "ifc_parent_unique_id",
                  fme:get-attribute("_storey_id")
              )
          ]
      }
    CONSECUTIVE_GROUPS = Yes
    VISIBLE_QUERY_VALIDATE = Yes
    -> PythonCaller
Note: _storey_index (1-based) / 下層階から順番に 1, 2, 3, ...
PythonCaller
    HIDE_ATTRIBUTES = _hierarchy fme_feature_type _citygml_feature_type Description GlobalId LongName Name ObjectType Tag Elevation
    NEW_ATTRIBUTES = ifc_unique_id ifc_feature_type ifc_parent_feature_type _storey_index _storey_id _storey_name
    PYTHONSOURCE:
      import fme
      import fmeobjects, json, sys

      class FeatureProcessor(object):
          def __init__(self):
              pass

          def has_support_for(self, support_type: int):
              return support_type == fmeobjects.FME_SUPPORT_FEATURE_TABLE_SHIM

          def input(self, feature: fmeobjects.FMEFeature):
              gmlId = feature.getAttribute('__bldg_gml_id')
              bname = feature.getAttribute('fme_basename')
              storeyToElements = {} # {storey_id : [elements list]}
              storeyToElevation = {} # {storey_id : elevation}
              storeyToZmin = {} # {story_id : zmin}

              def collect_elements(element, parent_feature_type, sid, sname):
                  feature_type = element['ifc_feature_type']
                  attrib = {
                      '__bldg_gml_id' : gmlId,
                      'fme_basename' : bname,
                      'ifc_unique_id' : element['ifc_unique_id'],
                      'ifc_feature_type' : feature_type,
                      'ifc_parent_feature_type' : parent_feature_type,
                      '_storey_id' : sid,
                      '_storey_name' : sname,
                  }
                  newFeature = fmeobjects.FMEFeature()
                  for attr, value in attrib.items():
                      newFeature.setAttribute(attr, value)
                  storeyToElements.setdefault(sid, []).append(newFeature)

                  # storeyごとの各オブジェクト最低標高の最小値を、当該storeyの標高代表値として
                  # storey_indexの順番を決定する。
                  # ただし、zmin と zmax が等しいエレメント (ジオメトリがない可能性あり) は除く。
                  zmax = element['zmax']
                  zmin = element['zmin']
                  if zmin < zmax and zmin < storeyToZmin.get(sid, sys.float_info.max):
                      storeyToZmin[sid] = zmin

                  for child in element['elements']:
                      collect_elements(child, feature_type, sid, sname)

              noElCount = 0
              for storey in json.loads(feature.getAttribute('_hierarchy')):
                  stype = storey['ifc_feature_type']
                  sid = storey['ifc_unique_id']
                  sname = storey['name']
                  el = storey['elevation']
                  try:
                      el = float(el)
                      storeyToElevation[sid] = el
                  except:
                      noElCount += 1
                  for child in storey["elements"]:
                      collect_elements(child, stype, sid, sname)

              if 0 < noElCount:
                  storeyToElevation = storeyToZmin
              for sindex, (_, sid) in enumerate(sorted([(z, sid) for sid, z in storeyToElevation.items()])):
                  i = sindex + 1
                  for newFeature in storeyToElements.get(sid, []):
                      newFeature.setAttribute('_storey_index', i)
                      self.pyoutput(newFeature)
      \
          def close(self):
              pass

          def process_group(self):
              pass
    PYTHONSYMBOL = FeatureProcessor
    SHOW_ERROR_INDICATORS = No
    -> FeatureMerger [REQUESTOR]
Note: Feature Merge Type: / Attributes and Geometry
FeatureMerger
    ATTR_ACCUM_MODE = Merge Supplier
    ATTR_CONFLICT_RES_LOOKUP = REQUESTOR_IF_CONFLICT
    GROUP_BY = fme_basename
    IGNORE_NULLS = No
    JOIN_KEYS = @Value(ifc_unique_id) @Value(ifc_unique_id) AUTO
    MERGE_TYPE_VAL = GEOM_AND_ATTRS
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes and Geometry
    MERGED -> Tester_13

Bookmark: ソリッドはすべて BrepSolid に置換, ソリッド以外は Face 抽出
BrepSolidReplacer
    -> NullAttributeMapper
    <Unfiltered> -> GeometryFilter
    <Rejected> -> Junction_31
GeometryFilter
    FILTER_MODE = COMPLETE
    FILTER_MULTI = FILTER_TYPES]Face]FILTER_TYPES_Complete]Face]INSTANCES]INSTANCE
    FILTER_TYPES = Face
    FILTER_TYPES_Complete = Face
    INSTANCES = INSTANCE
    SHOW_ERROR_INDICATORS = No
    Face -> NullAttributeMapper
Junction_31
    SHOW_ERROR_INDICATORS = No

Bookmark: CityGMLフィーチャータイプ名設定
Note: Window
AttributeCreator_2
    ATTR_TABLE = SET_TO _citygml_feature_type (buffer) = Window
    SHOW_ERROR_INDICATORS = No
    -> GeometryPartExtractor_2
Note: ClosureSurface
AttributeCreator_3
    ATTR_TABLE = SET_TO _citygml_feature_type (buffer) = ClosureSurface
    SHOW_ERROR_INDICATORS = No
    -> GeometryPartExtractor_2
Note: ClosureSurface
AttributeCreator_4
    ATTR_TABLE = SET_TO _citygml_feature_type (buffer) = ClosureSurface
    SHOW_ERROR_INDICATORS = No
    -> GeometryPartExtractor_4
    -> GeometryPartExtractor_2
Note: Door
AttributeCreator
    ATTR_TABLE = SET_TO _citygml_feature_type (buffer) = Door
    SHOW_ERROR_INDICATORS = No
    -> GeometryPartExtractor_2

Bookmark: IfcCoverring, IfcSlab の「穴」の形状を上下に一定距離引き延ばしたソリッド作成
Note: OpeningElement のない Slab, Covering の開口部（ただの穴, ClosureSurface）
GeometryPartExtractor_4
    GQUERY:
      for $geom in //geometry
      where $geom/@fme_geometry_type = 'IFMEFace'
      return number($geom/@fme_id)
    SHOW_ERROR_INDICATORS = No
    EXTRACTED -> PlanarityFilter_4
PlanarityFilter_4
    ANGULAR_TOLERANCE = 20
    ANGULAR_TOLERANCE_CHOICE_LOOKUP = CUSTOM
    OUTPUT_LOOKUP = EXPOSE_SURFACE_NORMAL
    SHOW_ERROR_INDICATORS = No
    THICKNESS_TOLERANCE = 30
    THICKNESS_TOLERANCE_CHOICE_LOOKUP = CUSTOM
    ANGULAR_TOLERANCE_CHOICE = Custom
    OUTPUT_NORMAL = Yes
    THICKNESS_TOLERANCE_CHOICE = Custom
    PLANAR -> Tester_4
Tester_4
    BOOL_OP = OR
    PRESERVE_FEATURE_ORDER_LOOKUP = PER_OUTPUT_PORT
    SHOW_ERROR_INDICATORS = No
    TEST_CLAUSE = TEST 0.5 < @abs(@Value(_surfaceNormalZ))
    TEST_MODE = TEST
    PASSED -> GeometryPartExtractor_5
GeometryPartExtractor_5
    GQUERY:
      for $geom in //geometry
      where $geom/@fme_geometry_type = 'IFMEDonut'
      return number($geom/@fme_id)
    SHOW_ERROR_INDICATORS = No
    EXTRACTED -> DonutHoleExtractor
DonutHoleExtractor
    DEAGGREGATE_INPUT = Yes
    SHOW_ERROR_INDICATORS = No
    HOLE -> OrientationExtractor
OrientationExtractor
    ORIENTATION = _orientation
    SHOW_ERROR_INDICATORS = No
    -> AttributeFilter_6
Note: 上面と下面に分岐
AttributeFilter_6
    ATTR_NAME = _orientation
    ATTR_VALUES = right_hand_rule,left_hand_rule,<Empty>,<Missing>,<Null>,<Unfiltered>
    PRESERVE_FEATURE_ORDER_LOOKUP = PER_OUTPUT_PORT
    SHOW_ERROR_INDICATORS = No
    right_hand_rule -> PlanarityFilter_5
    left_hand_rule -> SpatialFilter [Candidate]
PlanarityFilter_5
    ANGULAR_TOLERANCE = 20
    ANGULAR_TOLERANCE_CHOICE_LOOKUP = CUSTOM
    OUTPUT_LOOKUP = HIDE_SURFACE_NORMAL
    SHOW_ERROR_INDICATORS = No
    THICKNESS_TOLERANCE = 30
    THICKNESS_TOLERANCE_CHOICE_LOOKUP = CUSTOM
    ANGULAR_TOLERANCE_CHOICE = Custom
    OUTPUT_NORMAL = No
    THICKNESS_TOLERANCE_CHOICE = Custom
    PLANAR -> AttributeManager_6
AttributeManager_6
    ATTR_TABLE:
      REMOVE _surfaceNormalX (real64)
      REMOVE _surfaceNormalY (real64)
      REMOVE _surfaceNormalZ (real64)
      RENAME_SET_VALUE _pointOnSurfaceX > _pointOnSurfaceX1 (real64)
      RENAME_SET_VALUE _pointOnSurfaceY > _pointOnSurfaceY1 (real64)
      RENAME_SET_VALUE _pointOnSurfaceZ > _pointOnSurfaceZ1 (real64)
    SHOW_ERROR_INDICATORS = No
    -> CenterPointReplacer_2
CenterPointReplacer_2
    POINTTYPE = CENTER
    SHOW_ERROR_INDICATORS = No
    POINT -> SpatialFilter [Filter]
SpatialFilter
    AGGREGATE_HANDLING = Yes
    ATTR_CONFLICT_RES_LOOKUP = CANDIDATE_IF_CONFLICT
    BOOL_OP = OR
    BOUNDING_BOX = NO
    CURVE_BOUNDARY_RULE = ENDPOINTS_MOD2
    GROUP_BY = ifc_unique_id
    MULTI_BASE = YES
    PREDATTR = _predicate
    PREDICATES = INTERSECTS
    PRESERVE_FEATURE_ORDER_LOOKUP = PER_OUTPUT_PORT
    SHOW_ERROR_INDICATORS = No
    ATTR_ACCUM_MODE = Merge Filter
    ATTR_CONFLICT_RES = Use Candidate
    BASE_TYPE = Multiple Filters
    CURVE_BOUNDARY_RULE_PARAM = Default Rule
    PASS_CRITERIA = Pass Against One Filter
    USE_BOUNDING_BOX = No
    PASSED -> PythonCaller_2
Note: 厚みの計算 / ポイントと面の距離として求める。
PythonCaller_2
    NEW_ATTRIBUTES = __thickness
    PYTHONSOURCE:
      import fme
      import fmeobjects, math

      class ThicknessCalculator(object):
          def __init__(self):
              pass

          def has_support_for(self, support_type: int):
              return support_type == fmeobjects.FME_SUPPORT_FEATURE_TABLE_SHIM

          def input(self, feature: fmeobjects.FMEFeature):
              x0 = feature.getAttribute('_pointOnSurfaceX')
              y0 = feature.getAttribute('_pointOnSurfaceY')
              z0 = feature.getAttribute('_pointOnSurfaceZ')
              a = feature.getAttribute('_surfaceNormalX')
              b = feature.getAttribute('_surfaceNormalY')
              c = feature.getAttribute('_surfaceNormalZ')
              d = -(a * x0 + b * y0 + c * z0)

              x1 = feature.getAttribute('_pointOnSurfaceX1')
              y1 = feature.getAttribute('_pointOnSurfaceY1')
              z1 = feature.getAttribute('_pointOnSurfaceZ1')

              t = abs(a*x1 + b*y1 + c*z1 + d)/math.sqrt(a**2 + b**2 + c**2)
              feature.setAttribute('__thickness', t)

              self.pyoutput(feature)

          def close(self):
              pass

          def process_group(self):
              pass
    PYTHONSYMBOL = ThicknessCalculator
    SHOW_ERROR_INDICATORS = No
    -> FaceReplacer
FaceReplacer
    ANGULAR_TOLERANCE = 20
    ANGULAR_TOLERANCE_CHOICE_LOOKUP = CUSTOM
    SHOW_ERROR_INDICATORS = No
    THICKNESS_TOLERANCE = 30
    THICKNESS_TOLERANCE_CHOICE_LOOKUP = CUSTOM
    ANGULAR_TOLERANCE_CHOICE = Custom
    THICKNESS_TOLERANCE_CHOICE = Custom
    -> Offsetter
Offsetter
    MODE_LOOKUP = CARTESIAN
    SHOW_ERROR_INDICATORS = No
    XOFF = @Value(_surfaceNormalX)*(@Value(__thickness)*0.5 - $(OPENING_EXTENSION_DISTANCE_H))
    YOFF = @Value(_surfaceNormalY)*(@Value(__thickness)*0.5 - $(OPENING_EXTENSION_DISTANCE_H))
    ZOFF = @Value(_surfaceNormalZ)*(@Value(__thickness)*0.5 - $(OPENING_EXTENSION_DISTANCE_H))
    MODE = Cartesian Coordinate
    OFFSET -> Extruder_3
Extruder_3
    DIRECTION_LOOKUP = AUTO
    DISTANCE = $(OPENING_EXTENSION_DISTANCE_H)*2
    SHOW_ERROR_INDICATORS = No
    DIRECTION = Auto
    EXTRUDED -> AttributeManager_7
Note: __orientation = horizontal
AttributeManager_7
    ATTR_TABLE:
      REMOVE _pointOnSurfaceX1 (real64)
      REMOVE _pointOnSurfaceY1 (real64)
      REMOVE _pointOnSurfaceZ1 (real64)
      REMOVE _orientation (buffer)
      REMOVE fme_feature_type (char(50))
      REMOVE _surfaceNormalX (real64)
      REMOVE _surfaceNormalY (real64)
      REMOVE _surfaceNormalZ (real64)
      REMOVE _pointOnSurfaceX (real64)
      REMOVE _pointOnSurfaceY (real64)
      REMOVE _pointOnSurfaceZ (real64)
      REMOVE _predicate (buffer)
      REMOVE __thickness (buffer)
      SET_TO __orientation (buffer) = horizontal
    SHOW_ERROR_INDICATORS = No
    -> Junction_11

Bookmark: （ほぼ）水平面（床、天井）か垂直面（壁）かを判定
PlanarityFilter
    ANGULAR_TOLERANCE = 20
    ANGULAR_TOLERANCE_CHOICE_LOOKUP = CUSTOM
    OUTPUT_LOOKUP = EXPOSE_SURFACE_NORMAL
    SHOW_ERROR_INDICATORS = No
    THICKNESS_TOLERANCE = 30
    THICKNESS_TOLERANCE_CHOICE_LOOKUP = CUSTOM
    ANGULAR_TOLERANCE_CHOICE = Custom
    OUTPUT_NORMAL = Yes
    THICKNESS_TOLERANCE_CHOICE = Custom
    PLANAR -> AttributeManager
AttributeManager
    ATTR_TABLE:
      REMOVE fme_feature_type (char(50))
      SET_TO __orientation (varchar(200)) = FME_CONDITIONAL:DEFAULT_VALUE'horizontal'BOOL_OP;OR;COMPOSITE_TEST;1;TEST @abs(@Value(_surfaceNormalZ)) < 0.1'vertical'FME_NUM_CONDITIONS2___
      RENAME_SET_VALUE _surfaceNormalX > __normal_x (real64)
      RENAME_SET_VALUE _surfaceNormalY > __normal_y (real64)
      RENAME_SET_VALUE _surfaceNormalZ > __normal_z (real64)
      REMOVE _pointOnSurfaceX (real64)
      REMOVE _pointOnSurfaceY (real64)
      REMOVE _pointOnSurfaceZ (real64)
      SET_TO __rounded_normal_x (varchar(200)) = @Evaluate(@abs(@round(@Value(__normal_x)*100)))
      SET_TO __rounded_normal_y (varchar(200)) = @Evaluate(@abs(@round(@Value(__normal_y)*100)))
    SHOW_ERROR_INDICATORS = No
    -> AttributeFilter_2

Bookmark: 屋内 (IntBuildingInstallation), 屋外 (BuildingInstallation) に分割, 詳細LOD設定に該当するフィーチャーを選択
Note: 屋内と屋外に分割
Clipper_5
    ADD_NODATA = YES
    ATTR_ACCUM_MODE = PREFIX_CLIPPER
    BOUNDARY_CASES = INSIDE
    CLEANING_TOLERANCE_LOOKUP = AUTO
    CLIPPED_ATTR = _clipped
    CLIPPERS_FIRST = NO
    CLIPPER_PREFIX = _room_
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    SHOW_ERROR_INDICATORS = No
    Z_VAL_SOURCE = CANDIDATE
    CLEANING_TOLERANCE = Automatic
    MISSING_M_MODE = Linear Interpolation
    MISSING_Z_MODE = Planar Interpolation
    INSIDE -> Tester
    OUTSIDE -> Tester_12
Note: 複数の屋内空間に分割されたものは、元の形状に戻す。
Tester
    BOOL_OP = OR
    PRESERVE_FEATURE_ORDER_LOOKUP = PER_OUTPUT_PORT
    SHOW_ERROR_INDICATORS = No
    TEST_CLAUSE = TEST @Value(_clipped) = yes
    TEST_MODE = TEST
    PASSED -> GeometryFilter_3
    FAILED -> AttributeManager_12
GeometryFilter_3
    FILTER_MODE = SIMPLE
    FILTER_MULTI = FILTER_TYPES]Surface Solid]FILTER_TYPES_Simple]Surface Solid
    FILTER_TYPES = Surface Solid
    FILTER_TYPES_Simple = Surface Solid
    SHOW_ERROR_INDICATORS = No
    Surface -> SurfaceDissolver
    Solid -> SolidDissolver_2
SurfaceDissolver
    ACCUM_INPUT_ATTRS_LOOKUP = One
    DEAGGREGATE_INPUT = Yes
    GROUP_BY = __bldg_gml_id __temp_id
    MATCHING_APPS = No
    NORMAL_TOLERANCE = 0
    OFFSET_TOLERANCE = 0
    SEPARATE_SURFACES = No
    SHOW_ERROR_INDICATORS = No
    ACCUM_INPUT_ATTRS = Use Attributes From One Feature
    SURFACE -> Aggregator_7
SolidDissolver_2
    ACCUM_INPUT_ATTRS = ONE
    DEAGGREGATE_INPUT = Yes
    GROUP_BY = __bldg_gml_id __temp_id
    SHOW_ERROR_INDICATORS = No
    SOLID -> Aggregator_7
Aggregator_7
    ACCUM_ATTRS = One
    AGGREGATE_TYPE = Homogeneous Collection (If Possible)
    GROUP_BY = __bldg_gml_id __temp_id
    MODE = Geometry - Assemble One Level
    SEP = ,
    SHOW_ERROR_INDICATORS = No
    ACCUM_ATTRS_NAME = Use Attributes From One Feature
    AGGREGATE -> AttributeManager_12
Tester_12
    BOOL_OP = OR
    PRESERVE_FEATURE_ORDER_LOOKUP = PER_OUTPUT_PORT
    SHOW_ERROR_INDICATORS = No
    TEST_CLAUSE = TEST @Value(_clipped) = yes
    TEST_MODE = TEST
    PASSED -> Aggregator_8
    FAILED -> Junction_43
Aggregator_8
    ACCUM_ATTRS = One
    AGGREGATE_TYPE = Homogeneous Collection (If Possible)
    GROUP_BY = __bldg_gml_id __temp_id
    MODE = Geometry - Assemble One Level
    SEP = ,
    SHOW_ERROR_INDICATORS = No
    ACCUM_ATTRS_NAME = Use Attributes From One Feature
    AGGREGATE -> Junction_43
Junction_43
    SHOW_ERROR_INDICATORS = No
    -> AttributeManager_13

Bookmark: BuildingFurniture
AttributeManager_14
    ATTR_TABLE:
      REMOVE ifc_parent_unique_id (buffer)
      REMOVE ifc_feature_type (buffer)
      REMOVE ifc_parent_feature_type (buffer)
      REMOVE _storey_index (buffer)
      REMOVE _storey_id (buffer)
      REMOVE _storey_name (buffer)
      REMOVE GlobalId (char(22))
      REMOVE Name (buffer)
      REMOVE Description (buffer)
      REMOVE ObjectType (buffer)
      REMOVE LongName (buffer)
      REMOVE Tag (buffer)
      REMOVE fme_feature_type (char(50))
      REMOVE _zmin (real64)
      REMOVE _zmax (real64)
      REMOVE ElementType (buffer)
      REMOVE PredefinedType (buffer)
      REMOVE ShapeType (buffer)
      REMOVE OperationType (buffer)
    SHOW_ERROR_INDICATORS = No
    -> FeatureMerger_8 [SUPPLIER]
Tester_11
    BOOL_OP = OR
    PRESERVE_FEATURE_ORDER_LOOKUP = PER_OUTPUT_PORT
    SHOW_ERROR_INDICATORS = No
    TEST_CLAUSE = TEST 4.2 <= $(DEST_LOD)
    TEST_MODE = TEST
    PASSED -> FeatureMerger_8 [REQUESTOR]
Note: 所属先のRoomの / __room_gml_id を 付与。
FeatureMerger_8
    ATTR_ACCUM_MODE = Merge Supplier
    ATTR_CONFLICT_RES_LOOKUP = REQUESTOR_IF_CONFLICT
    GROUP_BY = __bldg_gml_id fme_basename
    IGNORE_NULLS = No
    JOIN_KEYS = @Value(ifc_parent_unique_id) @Value(ifc_unique_id) AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> AttributeCreator_18
Note: __frn_gml_id
AttributeCreator_18
    ATTR_TABLE = SET_TO __frn_gml_id (varchar(200)) = frn_@UUID()
    SHOW_ERROR_INDICATORS = No
    -> GeometryPartExtractor_10

Bookmark: CityObjectGroup XMLテキスト作成
Junction_82
    SHOW_ERROR_INDICATORS = No
    -> Junction_83
Junction_83
    SHOW_ERROR_INDICATORS = No
    -> XMLTemplater [ROOM]
Note: IfcBuildingStorey
Junction_81
    SHOW_ERROR_INDICATORS = No
    -> AttributeManager_19
AttributeManager_19
    ATTR_TABLE:
      SET_TO __grp_gml_id (varchar(200)) = grp_@UUID()
      REMOVE fme_feature_type (char(50))
      SET_TO _storey_elevation (real64) = @Format(%.2f,@CurrentAttribute())
    SHOW_ERROR_INDICATORS = No
    -> Sampler
Sampler
    GROUP_BY = __bldg_gml_id fme_basename
    MODE = ORIGINAL
    RATE = 1
    SAMPLE_TYPE_MULTIPLIER = -1
    SHOW_ERROR_INDICATORS = No
    SAMPLE_MODE = No
    SAMPLE_TYPE_LONG = First N Features
    SAMPLED -> XMLTemplater [ROOT]
    SAMPLED -> XMLTemplater [STOREY]
    NOT_SAMPLED -> XMLTemplater [STOREY]
XMLTemplater
    CONSECUTIVE_GROUP_LOOKUP = YES
    GROUP_BY = fme_basename __bldg_gml_id
    OUTPUT_XML_HEADER_LOOKUP = YES
    QUERY_VALIDATE = YES
    RESULT_ATTRIBUTE = _xml_fragment
    ROOM_QUERY_EXPR:
      declare namespace grp="http://www.opengis.net/citygml/cityobjectgroup/2.0";
      declare namespace xlink="http://www.w3.org/1999/xlink";
      <grp:groupMember xlink:href="{'#'||fme:get-attribute("__room_gml_id")}" />
    ROOT_QUERY_EXPR:
      <core:CityModel xmlns:tran="http://www.opengis.net/citygml/transportation/2.0" xmlns:brid="http://www.opengis.net/citygml/bridge/2.0" xmlns:frn="http://www.opengis.net/citygml/cityfurniture/2.0" xmlns:wtr="http://www.opengis.net/citygml/waterbody/2.0" xmlns:sch="http://www.ascc.net/xml/schematron" xmlns:veg="http://www.opengis.net/citygml/vegetation/2.0" xmlns:xlink="http://www.w3.org/1999/xlink" xmlns:tun="http://www.opengis.net/citygml/tunnel/2.0" xmlns:tex="http://www.opengis.net/citygml/texturedsurface/2.0" xmlns:gml="http://www.opengis.net/gml" xmlns:gen="http://www.opengis.net/citygml/generics/2.0" xmlns:dem="http://www.opengis.net/citygml/relief/2.0" xmlns:app="http://www.opengis.net/citygml/appearance/2.0" xmlns:luse="http://www.opengis.net/citygml/landuse/2.0" xmlns:uro="https://www.geospatial.jp/iur/uro/3.1" xmlns:xAL="urn:oasis:names:tc:ciq:xsdschema:xAL:2.0" xmlns:bldg="http://www.opengis.net/citygml/building/2.0" xmlns:smil20="http://www.w3.org/2001/SMIL20/" xmlns:xsi="http://www.w3.org/2001/XMLSchema-instance" xmlns:smil20lang="http://www.w3.org/2001/SMIL20/Language" xmlns:pbase="http://www.opengis.net/citygml/profiles/base/2.0" xmlns:core="http://www.opengis.net/citygml/2.0" xmlns:grp="http://www.opengis.net/citygml/cityobjectgroup/2.0">
      {
          fme:process-features("STOREY")
      }
      </core:CityModel>
    SHOW_ERROR_INDICATORS = No
    STOREY_QUERY_EXPR:
      declare namespace gml="http://www.opengis.net/gml";
      declare namespace core="http://www.opengis.net/citygml/2.0";
      declare namespace grp="http://www.opengis.net/citygml/cityobjectgroup/2.0";
      declare namespace uro="https://www.geospatial.jp/iur/uro/3.1";
      declare namespace xlink="http://www.w3.org/1999/xlink";
      <core:cityObjectMember>
          <grp:CityObjectGroup gml:id="{fme:get-attribute("__grp_gml_id")}">
              <gml:name>{fme:get-attribute("_storey_name")}</gml:name>
              {
                  fme:process-features("ROOM", '_storey_id', fme:get-attribute("_storey_id"))
              }
              <grp:parent xlink:href="{'#'||fme:get-attribute("__bldg_gml_id")}" />
              <uro:ifcBuildingStoreyAttribute>
                  <uro:IfcBuildingStorey>
                      <uro:globalId>{fme:get-attribute("_storey_global_id")}</uro:globalId>
                      <uro:name>{fme:get-attribute("_storey_name")}</uro:name>
                      {
                          if (fme:has-attribute('_storey_elevation')) then
                          <uro:elevation uom="m">{fme:get-attribute("_storey_elevation")}</uro:elevation> else ()
                      }
                  </uro:IfcBuildingStorey>
              </uro:ifcBuildingStoreyAttribute>
          </grp:CityObjectGroup>
      </core:cityObjectMember>
    CONSECUTIVE_GROUPS = Yes
    OUTPUT_XML_HEADER = Yes
    VISIBLE_QUERY_VALIDATE = Yes
    -> AttributeManager_CityObjectGroup
AttributeManager_CityObjectGroup
    ATTR_TABLE:
      REMOVE __grp_gml_id (varchar(200))
      REMOVE _storey_global_id (char(22))
      REMOVE _storey_name (buffer)
      REMOVE _storey_description (buffer)
      REMOVE _storey_object_type (buffer)
      REMOVE _storey_long_name (buffer)
      REMOVE _storey_tag (buffer)
      REMOVE _storey_id (buffer)
      REMOVE _storey_elevation (real64)
    SHOW_ERROR_INDICATORS = No
    -> Junction_135

Bookmark: 階ごとの屋内空間のフットプリント
Aggregator_9
    ACCUM_ATTRS = None
    AGGREGATE_TYPE = Homogeneous Collection (If Possible)
    GROUP_BY = _storey_id _storey_index _storey_name fme_basename
    MODE = Geometry - Assemble One Level
    SEP = ,
    SHOW_ERROR_INDICATORS = No
    ACCUM_ATTRS_NAME = Drop Incoming Attributes
    AGGREGATE -> BoundsExtractor_3
BoundsExtractor_3
    SHOW_ERROR_INDICATORS = No
    ZMAX = _zmax
    ZMIN = _zmin
    -> SurfaceFootprintReplacer_5
SurfaceFootprintReplacer_5
    OFFSET_Z_LOOKUP = 0
    SHADOW_TYPE = OVERHEAD
    SHOW_ERROR_INDICATORS = No
    OFFSET_Z = 0
    SHADOW_MODE = Overhead Shadow
    FOOTPRINT -> Bufferer_5
Bufferer_5
    ANGLE = 22.5
    CAP_STYLE_LOOKUP = CAP_ARC
    CORNER_STYLE_LOOKUP = JOIN_MITER
    GROUP_BY = _storey_index fme_basename
    MITER_LIMIT = 2
    MODE = AREA
    OFFSET = 500
    OFFSET_UNITS = NONE
    PRECISION = APPROX
    SHOW_ERROR_INDICATORS = No
    CAP_STYLE = Arc
    CORNER_STYLE = Miter
    BUFFERED -> Bufferer_6
Bufferer_6
    ANGLE = 22.5
    CAP_STYLE_LOOKUP = CAP_ARC
    CORNER_STYLE_LOOKUP = JOIN_MITER
    MITER_LIMIT = 2
    MODE = AREA
    OFFSET = -500
    OFFSET_UNITS = NONE
    PRECISION = APPROX
    SHOW_ERROR_INDICATORS = No
    CAP_STYLE = Arc
    CORNER_STYLE = Miter
    BUFFERED -> Generalizer_2
Generalizer_2
    ALG = Douglas
    PRESERVE = No
    PRESERVE_PATHS_LOOKUP = NO
    SHOW_ERROR_INDICATORS = No
    TOLERANCE = 1
    ALG_TEXT = Douglas (Generalize)
    PRESERVE_PATHS = No
    -> DonutHoleExtractor_3
DonutHoleExtractor_3
    DEAGGREGATE_INPUT = Yes
    SHOW_ERROR_INDICATORS = No
    OUTERSHELL -> Bufferer_3

Bookmark: 階ごとの屋内空間 + 外壁外周のフットプリント
Aggregator_5
    ACCUM_ATTRS = None
    AGGREGATE_TYPE = Homogeneous Collection (If Possible)
    GROUP_BY = _storey_id _storey_index _storey_name fme_basename
    MODE = Geometry - Assemble One Level
    SEP = ,
    SHOW_ERROR_INDICATORS = No
    ACCUM_ATTRS_NAME = Drop Incoming Attributes
    AGGREGATE -> BoundsExtractor_2
BoundsExtractor_2
    SHOW_ERROR_INDICATORS = No
    ZMAX = _zmax
    ZMIN = _zmin
    -> SurfaceFootprintReplacer_3
SurfaceFootprintReplacer_3
    OFFSET_Z_LOOKUP = 0
    SHADOW_TYPE = OVERHEAD
    SHOW_ERROR_INDICATORS = No
    OFFSET_Z = 0
    SHADOW_MODE = Overhead Shadow
    FOOTPRINT -> Bufferer
Bufferer
    ANGLE = 22.5
    CAP_STYLE_LOOKUP = CAP_ARC
    CORNER_STYLE_LOOKUP = JOIN_MITER
    GROUP_BY = _storey_index fme_basename
    MITER_LIMIT = 2
    MODE = AREA
    OFFSET = 500
    OFFSET_UNITS = NONE
    PRECISION = APPROX
    SHOW_ERROR_INDICATORS = No
    CAP_STYLE = Arc
    CORNER_STYLE = Miter
    BUFFERED -> Bufferer_2
Bufferer_2
    ANGLE = 22.5
    CAP_STYLE_LOOKUP = CAP_ARC
    CORNER_STYLE_LOOKUP = JOIN_MITER
    MITER_LIMIT = 2
    MODE = AREA
    OFFSET = -500
    OFFSET_UNITS = NONE
    PRECISION = APPROX
    SHOW_ERROR_INDICATORS = No
    CAP_STYLE = Arc
    CORNER_STYLE = Miter
    BUFFERED -> Generalizer
Generalizer
    ALG = Douglas
    PRESERVE = No
    PRESERVE_PATHS_LOOKUP = NO
    SHOW_ERROR_INDICATORS = No
    TOLERANCE = 1
    ALG_TEXT = Douglas (Generalize)
    PRESERVE_PATHS = No
    -> DonutHoleExtractor_2
DonutHoleExtractor_2
    DEAGGREGATE_INPUT = Yes
    SHOW_ERROR_INDICATORS = No
    OUTERSHELL -> Junction_38
    OUTERSHELL -> Junction_63

Bookmark: 各階の外周を上下に引き伸ばした立体
3DForcer
    KEEPZVAL = No
    SHOW_ERROR_INDICATORS = No
    ZVALATTR = @Value(_zmin)-5000
    -> Extruder_5
Extruder_5
    DIRECTION_LOOKUP = VERTICAL
    DISTANCE = @Value(_zmax)-@Value(_zmin)+10000
    SHOW_ERROR_INDICATORS = No
    DIRECTION = Vertical
    EXTRUDED -> Clipper_2 [CLIPPER] [off]
    EXTRUDED -> ExpressionEvaluator

Bookmark: 各階の外周を若干縮小した形状上下に引き伸ばした立体
Bufferer_4
    ANGLE = 22.5
    CAP_STYLE_LOOKUP = CAP_ARC
    CORNER_STYLE_LOOKUP = JOIN_ARC
    MODE = AREA
    OFFSET = -50
    OFFSET_UNITS = NONE
    PRECISION = APPROX
    SHOW_ERROR_INDICATORS = No
    CAP_STYLE = Arc
    CORNER_STYLE = Arc
    BUFFERED -> 3DForcer_2
3DForcer_2
    KEEPZVAL = No
    SHOW_ERROR_INDICATORS = No
    ZVALATTR = @Value(_zmin)-5000
    -> Extruder_6
Extruder_6
    DIRECTION_LOOKUP = VERTICAL
    DISTANCE = @Value(_zmax)-@Value(_zmin)+10000
    SHOW_ERROR_INDICATORS = No
    DIRECTION = Vertical
    EXTRUDED -> Clipper_4 [CLIPPER] [off]

Bookmark: MultiSurface に変換
GeometryPartExtractor_9
    GQUERY:
      for $geom in //geometry
      where $geom/@fme_geometry_type = 'IFMEFace'
      return number($geom/@fme_id)
    SHOW_ERROR_INDICATORS = No
    EXTRACTED -> AttributeCreator_15
AttributeCreator_15
    ATTR_TABLE = SET_TO gml_id (varchar(200)) = face_@UUID()
    SHOW_ERROR_INDICATORS = No
    -> GeometryPropertySetter_3
GeometryPropertySetter_3
    DO_REMOVE_ATTR = *
    GQUERY:
      for $geom in //geometry
      where $geom/count(parent::geometry) = 0
      return number($geom/@fme_id)
    OVERWRITE_CHOICE_OPT = yes
    SETTYPE_PARAM = Traits From Attributes
    SHOW_ERROR_INDICATORS = No
    SRC_ATTRS = gml_id
    OVERWRITE_CHOICE = Yes
    REMOVE_ATTRIBUTE = Yes
    SET -> Aggregator_Installation
Aggregator_Installation
    ACCUM_ATTRS = One
    AGGREGATE_TYPE = Homogeneous Collection (If Possible)
    GROUP_BY = _inst_gml_id
    MODE = Geometry - Assemble One Level
    SEP = ,
    SHOW_ERROR_INDICATORS = No
    ACCUM_ATTRS_NAME = Use Attributes From One Feature
    AGGREGATE -> AttributeManager_Installation

Bookmark: MultiSurface に変換
GeometryPartExtractor_10
    GQUERY:
      for $geom in //geometry
      where $geom/@fme_geometry_type = 'IFMEFace'
      return number($geom/@fme_id)
    SHOW_ERROR_INDICATORS = No
    EXTRACTED -> AttributeCreator_17
AttributeCreator_17
    ATTR_TABLE = SET_TO gml_id (varchar(200)) = face_@UUID()
    SHOW_ERROR_INDICATORS = No
    -> GeometryPropertySetter_6
GeometryPropertySetter_6
    DO_REMOVE_ATTR = *
    GQUERY:
      for $geom in //geometry
      where $geom/count(parent::geometry) = 0
      return number($geom/@fme_id)
    OVERWRITE_CHOICE_OPT = yes
    SETTYPE_PARAM = Traits From Attributes
    SHOW_ERROR_INDICATORS = No
    SRC_ATTRS = gml_id
    OVERWRITE_CHOICE = Yes
    REMOVE_ATTRIBUTE = Yes
    SET -> Aggregator_Furniture
Aggregator_Furniture
    ACCUM_ATTRS = One
    AGGREGATE_TYPE = Homogeneous Collection (If Possible)
    GROUP_BY = __bldg_gml_id fme_basename __frn_gml_id
    MODE = Geometry - Assemble One Level
    SEP = ,
    SHOW_ERROR_INDICATORS = No
    ACCUM_ATTRS_NAME = Use Attributes From One Feature
    AGGREGATE -> AttributeManager_Furniture

Bookmark: CodeType型属性のコード取得
AttributeValueMapper_ElementType
    DEFAULT_VALUE = @Value(fme_feature_type)
    LUT = IfcBeam,BE_01,IfcColumn,BE_02,IfcCurtainWall,BE_03,IfcDoor,BE_04,IfcPlate,BE_05,IfcRailing,BE_06,IfcRamp,BE_07,IfcRampFlight,BE_08,IfcRoof,BE_09,IfcSlab,BE_10,IfcStair,BE_11,IfcStairFlight,BE_12,IfcWall,BE_13,IfcWallStandardCase,BE_14,IfcWindow,BE_15,IfcBuildingElementProxy,BE_16,IfcTransportElement,BE_17
    MAPPING_DIRECTION = FORWARD
    SHOW_ERROR_INDICATORS = No
    SRC = fme_feature_type
    VAL_ATTR = _element_type_code
    -> AttributeValueMapper_PredefinedType
AttributeValueMapper_PredefinedType
    DEFAULT_VALUE = @Value(PredefinedType)
    LUT = COLUMN,01,PILASTER,02,PIERSTEM,03,PIERSTEM_SEGMENT,04,STANDCOLUMN,05,CEILING,11,FLOORING,12,CLADDING,13,ROOFING,14,MOLDING,15,SKIRTINGBOARD,16,INSULATION,17,MEMBRANE,18,SLEEVING,19,WRAPPING,20,COPING,21,HANDRAIL,30,GUARDRAIL,31,BALUSTRADE,32,FLOOR,41,ROOF,42,LANDING,43,BASESLAB,44
    MAPPING_DIRECTION = FORWARD
    SHOW_ERROR_INDICATORS = No
    SRC = PredefinedType
    VAL_ATTR = _predefined_type_code
    -> AttributeValueMapper_ShapeType
AttributeValueMapper_ShapeType
    DEFAULT_VALUE = @Value(ShapeType)
    LUT = STRAIGHT_RUN_RAMP,01,TWO_STRAIGHT_RUN_RAMP,02,QUARTER_TURN_RAMP,03,TWO_QUARTER_TURN_RAMP,04,HALF_TURN_RAMP,05,SPIRAL_RAMP,06,FLAT_ROOF,21,SHED_ROOF,22,GABLE_ROOF,23,HIP_ROOF,24,HIPPED_GABLE_ROOF,25,GAMBREL_ROOF,26,MANSARD_ROOF,27,BARREL_ROOF,28,RAINBOW_ROOF,29,BUTTEFLY_ROOF,30,PAVILION_ROOF,31,DOOM_ROOF,32,USERDEFINED,99,NOTDEFINED,00
    MAPPING_DIRECTION = FORWARD
    SHOW_ERROR_INDICATORS = No
    SRC = ShapeType
    VAL_ATTR = _shape_type_code
    -> FeatureTypeFilter_Attributes

Bookmark: uro:ifcBuildingAttribute/*
Junction_53
    SHOW_ERROR_INDICATORS = No
    -> GeometryPropertyExtractor_2
    -> PythonCaller_3
PythonCaller_3
    PYTHONSOURCE:
      import fme
      import fmeobjects, re

      TARGET_UNIT_TYPES = {
          'areaunit',
          'lengthunit',
          'planeangleunit',
          'volumeunit',
      }

      SI_PREFIXES = [
          'EXA',
          'PETA',
          'TERA',
          'GIGA',
          'MEGA',
          'KILO',
          'HCTO',
          'DECA',
          'DECI',
          'CENTI',
          'MILLI',
          'MICRO',
          'NANO',
          'PICO',
          'FEMTO',
          'ATTO',
      ]

      class UnitsInContextExtractor(object):
          def __init__(self):
              self.pattern = re.compile('^(%s)(.+)$' % '|'.join(SI_PREFIXES))

          def has_support_for(self, support_type: int):
              return support_type == fmeobjects.FME_SUPPORT_FEATURE_TABLE_SHIM

          def input(self, feature: fmeobjects.FMEFeature):
              index = 0
              for attr in [a for a in feature.getAllAttributeNames() if a.endswith('unit')]:
                  if attr in TARGET_UNIT_TYPES:
                      s = feature.getAttribute(attr).upper()
                      m = self.pattern.match(s)
                      prefix, name = (m.group(1), m.group(2)) if m else ('', s)
                      attrib = {
                          '_unit{%d}.type' % index : attr.upper(),
                          '_unit{%d}.prefix' % index : prefix,
                          '_unit{%d}.name' % index : name,
                      }
                      for k, v in attrib.items():
                          feature.setAttribute(k, v)
                      index += 1

              self.pyoutput(feature)

          def close(self):
              pass

          def process_group(self):
              pass
    PYTHONSYMBOL = UnitsInContextExtractor
    SHOW_ERROR_INDICATORS = No
    -> XMLTemplater_Building.IfcProject [ROOT]
XMLTemplater_Building.IfcProject
    OUTPUT_XML_HEADER_LOOKUP = NO
    QUERY_VALIDATE = YES
    RESULT_ATTRIBUTE = uro_ifc_building_attribute{0}
    ROOT_QUERY_EXPR:
      declare namespace uro="https://www.geospatial.jp/iur/uro/3.1";
      <uro:IfcProject>
          <uro:globalId>{fme:get-attribute("GlobalId")}</uro:globalId>
          <uro:name>{fme:get-attribute("Name")}</uro:name>
          {
              let $types := fme:get-list-attribute('_unit{}.type')
              let $prefixes := fme:get-list-attribute('_unit{}.prefix')
              let $names := fme:get-list-attribute('_unit{}.name')
              for $i in (1 to count($types))
              return
              <uro:unitsInContext>
                  <uro:IfcUnit>
                      <uro:unitType>{$types[$i]}</uro:unitType>
                      <uro:prefix>{$prefixes[$i]}</uro:prefix>
                      <uro:name>{$names[$i]}</uro:name>
                  </uro:IfcUnit>
              </uro:unitsInContext>
          }
      </uro:IfcProject>
    SHOW_ERROR_INDICATORS = No
    OUTPUT_XML_HEADER = No
    VISIBLE_QUERY_VALIDATE = Yes
    -> XMLDeepCleaner
XMLDeepCleaner
    FORMATTING_CHOICE = None
    KEEP_ROOT = Yes
    REMOVE_ALL_COMMENT = Yes
    REMOVE_XML_HEADER = no
    XML_ATTRIBUTE = @Value(uro_ifc_building_attribute{0})
    XML_OUTPUT_ATTR = uro_ifc_building_attribute{0}
    -> AttributeRemover
GeometryPropertyExtractor_2
    EXTRACTTYPE = EXTRACT_TRAITS
    GQUERY:
      for $geom in //geometry
      where $geom/count(parent::geometry) = 0
      return number($geom/@fme_id)
    PREFIX_EXTRACTED_TRAITS = Yes
    SHOW_ERROR_INDICATORS = No
    EXTRACTTYPE_PARAM = Traits
    EXTRACTED -> AttributeExposer_2
AttributeExposer_2
    ATTR_TABLE = ePSet_ProjectedCRS.Name,,ePSet_ProjectedCRS.Description,,ePSet_ProjectedCRS.GeodeticDatum,,ePSet_ProjectedCRS.VerticalDatum,,ePSet_ProjectedCRS.MapProjection,,ePSet_ProjectedCRS.MapZone,
    SHOW_ERROR_INDICATORS = No
    -> XMLTemplater_Building.IfcProjectedCRS [ROOT]
XMLTemplater_Building.IfcProjectedCRS
    OUTPUT_XML_HEADER_LOOKUP = NO
    QUERY_VALIDATE = YES
    RESULT_ATTRIBUTE = uro_ifc_building_attribute{1}
    ROOT_QUERY_EXPR:
      declare namespace uro="https://www.geospatial.jp/iur/uro/3.1";
      <uro:IfcProjectedCRS>
          <uro:name>{fme:get-attribute("ePSet_ProjectedCRS.Name")}</uro:name>
          <uro:description>{fme:get-attribute("ePSet_ProjectedCRS.Description")}</uro:description>
          <uro:geodeticDatum>{fme:get-attribute("ePSet_ProjectedCRS.GeodeticDatum")}</uro:geodeticDatum>
          <uro:virticalDatum>{fme:get-attribute("ePSet_ProjectedCRS.VerticalDatum")}</uro:virticalDatum>
          <uro:mapUnit>
          {
              if (fme:has-attribute("ePSet_ProjectedCRS.Name")) then 'm' else ()
          }
          </uro:mapUnit>
          <uro:mapProjection>{fme:get-attribute("ePSet_ProjectedCRS.MapProjection")}</uro:mapProjection>
          <uro:mapZone>{fme:get-attribute("ePSet_ProjectedCRS.MapZone")}</uro:mapZone>
      </uro:IfcProjectedCRS>
    SHOW_ERROR_INDICATORS = No
    OUTPUT_XML_HEADER = No
    VISIBLE_QUERY_VALIDATE = Yes
    -> XMLDeepCleaner_8
XMLDeepCleaner_8
    FORMATTING_CHOICE = None
    KEEP_ROOT = Yes
    REMOVE_ALL_COMMENT = Yes
    REMOVE_XML_HEADER = no
    XML_ATTRIBUTE = @Value(uro_ifc_building_attribute{1})
    XML_OUTPUT_ATTR = uro_ifc_building_attribute{1}
    -> AttributeRemover
XMLTemplater_Building.IfcSite
    OUTPUT_XML_HEADER_LOOKUP = NO
    QUERY_VALIDATE = YES
    RESULT_ATTRIBUTE = uro_ifc_building_attribute{2}
    ROOT_QUERY_EXPR:
      declare namespace uro="https://www.geospatial.jp/iur/uro/3.1";
      declare namespace core="http://www.opengis.net/citygml/2.0";
      declare namespace xAL="urn:oasis:names:tc:ciq:xsdschema:xAL:2.0";
      <uro:IfcSite>
          <uro:globalId>{fme:get-attribute("GlobalId")}</uro:globalId>
          <uro:name>{fme:get-attribute("Name")}</uro:name>
          <uro:siteAddress>
              <core:Address>
                  <core:xalAddress>
                      <xAL:AddressDetails>
                          <xAL:Country>
                              <xAL:CountryName>{fme:get-attribute("SiteAddress.Country")}</xAL:CountryName>
                              <xAL:Locality>
                                  <xAL:LocalityName Type="town">{
                                      concat(fme:get-attribute("SiteAddress.Region"),
                                          fme:get-attribute("SiteAddress.Town"),
                                          fme:get-attribute("SiteAddress.AddressLines"))
                                  }</xAL:LocalityName>
                              </xAL:Locality>
                          </xAL:Country>
                      </xAL:AddressDetails>
                  </core:xalAddress>
              </core:Address>
          </uro:siteAddress>
      </uro:IfcSite>
    SHOW_ERROR_INDICATORS = No
    OUTPUT_XML_HEADER = No
    VISIBLE_QUERY_VALIDATE = Yes
    -> XMLDeepCleaner_2
XMLDeepCleaner_2
    FORMATTING_CHOICE = None
    KEEP_ROOT = Yes
    REMOVE_ALL_COMMENT = Yes
    REMOVE_XML_HEADER = no
    XML_ATTRIBUTE = @Value(uro_ifc_building_attribute{2})
    XML_OUTPUT_ATTR = uro_ifc_building_attribute{2}
    -> AttributeRemover
XMLTemplater_IfcBuilding
    OUTPUT_XML_HEADER_LOOKUP = NO
    QUERY_VALIDATE = YES
    RESULT_ATTRIBUTE = uro_ifc_building_attribute{3}
    ROOT_QUERY_EXPR:
      declare namespace uro="https://www.geospatial.jp/iur/uro/3.1";
      declare namespace core="http://www.opengis.net/citygml/2.0";
      declare namespace xAL="urn:oasis:names:tc:ciq:xsdschema:xAL:2.0";
      <uro:IfcBuilding>
          <uro:globalId>{fme:get-attribute("GlobalId")}</uro:globalId>
          <uro:name>{fme:get-attribute("Name")}</uro:name>
          <uro:buildingAddress>
              <core:Address>
                  <core:xalAddress>
                      <xAL:AddressDetails>
                          <xAL:Country>
                              <xAL:CountryName>{fme:get-attribute("BuildingAddress.Country")}</xAL:CountryName>
                              <xAL:Locality>
                                  <xAL:LocalityName Type="town">{
                                      concat(fme:get-attribute("BuildingAddress.Region"),
                                          fme:get-attribute("BuildingAddress.Town"),
                                          fme:get-attribute("BuildingAddress.AddressLines"))
                                  }</xAL:LocalityName>
                              </xAL:Locality>
                          </xAL:Country>
                      </xAL:AddressDetails>
                  </core:xalAddress>
              </core:Address>
          </uro:buildingAddress>
      </uro:IfcBuilding>
    SHOW_ERROR_INDICATORS = No
    OUTPUT_XML_HEADER = No
    VISIBLE_QUERY_VALIDATE = Yes
    -> XMLDeepCleaner_3
XMLDeepCleaner_3
    FORMATTING_CHOICE = None
    KEEP_ROOT = Yes
    REMOVE_ALL_COMMENT = Yes
    REMOVE_XML_HEADER = no
    XML_ATTRIBUTE = @Value(uro_ifc_building_attribute{3})
    XML_OUTPUT_ATTR = uro_ifc_building_attribute{3}
    -> Aggregator_10

Bookmark: IFC属性結合
Note: GeometryRemover_3 : Output
Junction_93
    SHOW_ERROR_INDICATORS = No
    -> FeatureMerger_Building [SUPPLIER]
Note: GeometryRemover_2 : Output
Junction_91
    SHOW_ERROR_INDICATORS = No
    -> FeatureMerger_Others [SUPPLIER]
AttributeFilter
    ATTR_NAME = _citygml_feature_type
    ATTR_VALUES = Building,<Unfiltered>,<Empty>,<Missing>,<Null>
    PRESERVE_FEATURE_ORDER_LOOKUP = PER_OUTPUT_PORT
    SHOW_ERROR_INDICATORS = No
    Building -> FeatureMerger_Building [REQUESTOR]
    <UNFILTERED> -> FeatureMerger_Others [REQUESTOR]
FeatureMerger_Building
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> Junction_98
FeatureMerger_Others
    ATTR_ACCUM_MODE = Merge Supplier
    ATTR_CONFLICT_RES_LOOKUP = REQUESTOR_IF_CONFLICT
    CLEANING_TOLERANCE_LOOKUP = AUTO
    CONNECT_Z_MODE_LOOKUP = FIRST_WINS
    GEOM_TYPE_VAL = POLYGONS
    IGNORE_NULLS = No
    JOIN_KEYS = @Value(ifc_unique_id) @Value(ifc_unique_id) AUTO
    MERGE_TYPE_VAL = ATTRIBUTES
    PRESERVE_FEATURE_ORDER_LOOKUP = PER_OUTPUT_PORT
    PROCESS_DUPS = YES
    REJECT_NULL_MISSING_KEYS = No
    SHOW_ERROR_INDICATORS = No
    SUPPLIERS_FIRST = No
    ATTR_CONFLICT_RES = Use Requestor
    CLEANING_TOLERANCE = Automatic
    CONNECT_Z_MODE = First Wins
    GEOM_TYPE = Build Polygons
    MERGE_TYPE = Attributes Only
    MERGED -> Tester_14
    UNMERGED_REQUESTOR -> Junction_95

Bookmark: Door を単純化した直方体に変換（枠だけのドアはそのままでは開口部の向きが正しく求められないため、直方体に変換する。鉛直であることを前提とする）
Aggregator_3
    ACCUM_ATTRS = One
    AGGREGATE_TYPE = Homogeneous Collection (If Possible)
    GROUP_BY = ifc_unique_id
    MODE = Geometry - Assemble One Level
    SEP = ,
    SHOW_ERROR_INDICATORS = No
    ACCUM_ATTRS_NAME = Use Attributes From One Feature
    AGGREGATE -> SurfaceFootprintReplacer_4
SurfaceFootprintReplacer_4
    OFFSET_Z_LOOKUP = @Value(_zmin)
    SHADOW_TYPE = OVERHEAD
    SHOW_ERROR_INDICATORS = No
    OFFSET_Z = @Value(_zmin)
    SHADOW_MODE = Overhead Shadow
    FOOTPRINT -> HullAccumulator
HullAccumulator
    3DMODETYPE = MAKE3D
    ACCUM_INPUT_ATTRS_LOOKUP = One
    DEFAULTZ = @Value(_zmin)
    GROUP_BY = ifc_unique_id
    HULLTYPE = CONVEX
    SHOW_ERROR_INDICATORS = No
    3DMODE_PARAM = 3D
    ACCUM_INPUT_ATTRS = Use Attributes From One Feature
    HULLTYPE_PARAM = Convex ()
    HULL -> Extruder_2
Extruder_2
    DIRECTION_LOOKUP = AUTO
    DISTANCE = @Value(_zmax)-@Value(_zmin)
    SHOW_ERROR_INDICATORS = No
    DIRECTION = Auto
    EXTRUDED -> GeometryCoercer_2
GeometryCoercer_2
    GQUERY:
      for $geom in //geometry
      where $geom/count(parent::geometry) = 0
      return number($geom/@fme_id)
    KIND = fme_brep_solid
    SHOW_ERROR_INDICATORS = No
    COERCED -> Junction_32
    UNTOUCHED -> Junction_32

Bookmark: 扉、窓、壁類、スラブ等を構成する面のうち面積最大のものの法線によって水平面か鉛直面のどちらの開口部なのかを判定
Note: Extract Polygon
GeometryPartExtractor_2
    GQUERY:
      for $geom in //geometry
      where $geom/@fme_geometry_type = 'IFMEPolygon'
      return number($geom/@fme_id)
    SHOW_ERROR_INDICATORS = No
    EXTRACTED -> AreaCalculator
AreaCalculator
    AREA_ATTR = __area
    AREA_TYPE = Sloped Area
    MULT = 1
    SHOW_ERROR_INDICATORS = No
    -> Sorter
Sorter
    GROUP_BY = fme_basename
    SHOW_ERROR_INDICATORS = No
    SORT_PARM = __area NUMERIC DESCENDING
    SORTED -> DuplicateFilter
DuplicateFilter
    INPUT_ORDERED_CHOICE_LOOKUP = NO
    KEYATTR = ifc_unique_id
    PRESERVE_FEATURE_ORDER_LOOKUP = PER_OUTPUT_PORT
    SHOW_ERROR_INDICATORS = No
    INPUT_ORDERED_CHOICE = No
    UNIQUE -> PlanarityFilter_2
Note: 法線ベクトル計算
PlanarityFilter_2
    ANGULAR_TOLERANCE = 20
    ANGULAR_TOLERANCE_CHOICE_LOOKUP = CUSTOM
    OUTPUT_LOOKUP = EXPOSE_SURFACE_NORMAL
    SHOW_ERROR_INDICATORS = No
    THICKNESS_TOLERANCE = 30
    THICKNESS_TOLERANCE_CHOICE_LOOKUP = CUSTOM
    ANGULAR_TOLERANCE_CHOICE = Custom
    OUTPUT_NORMAL = Yes
    THICKNESS_TOLERANCE_CHOICE = Custom
    PLANAR -> AttributeManager_2
Note: __orientation / vertical : 鉛直の面 / horizontal : 水平の面 / __priority / 1 : Door, Window / 2 : その他 / __extension_distance / クリップ用ソリッドを作成する際に前後に押し出す距離
AttributeManager_2
    ATTR_TABLE:
      REMOVE fme_feature_type (char(50))
      REMOVE ifc_parent_feature_type (buffer)
      SET_TO __orientation (varchar(200)) = FME_CONDITIONAL:DEFAULT_VALUE'horizontal'BOOL_OP;OR;COMPOSITE_TEST;1;TEST @abs(@Value(_surfaceNormalZ)) < 0.1'vertical'FME_NUM_CONDITIONS2___
      SET_TO __priority (varchar(200)) = FME_CONDITIONAL:DEFAULT_VALUE'2'BOOL_OP;OR;COMPOSITE_TEST;1;TEST @Value(_citygml_feature_type) IN Door,Window'1'FME_NUM_CONDITIONS2___
      SET_TO __extension_distance (varchar(200)) = FME_CONDITIONAL:DEFAULT_VALUE'$(OPENING_EXTENSION_DISTANCE_H)'BOOL_OP;OR;COMPOSITE_TEST;1;TEST @Value(__orientation) = vertical'$(OPENING_EXTENSION_DISTANCE_V)'FME_NUM_CONDITIONS2___
      RENAME_SET_VALUE _surfaceNormalX > __normal_x (real64)
      RENAME_SET_VALUE _surfaceNormalY > __normal_y (real64)
      RENAME_SET_VALUE _surfaceNormalZ > __normal_z (real64)
      SET_TO __normal (varchar(200)) = @Evaluate(@abs(@round(@Value(__normal_x),0))) @Evaluate(@abs(@round(@Value(__normal_y),0))) @Evaluate(@abs(@round(@Value(__normal_z),0)))
      REMOVE _pointOnSurfaceX (real64)
      REMOVE _pointOnSurfaceY (real64)
      REMOVE _pointOnSurfaceZ (real64)
    SHOW_ERROR_INDICATORS = No
    -> Tester_2

Bookmark: 建具片面を前後に押し出したソリッドに変換
FaceReplacer_2
    ANGULAR_TOLERANCE_CHOICE_LOOKUP = AUTO
    SHOW_ERROR_INDICATORS = No
    THICKNESS_TOLERANCE_CHOICE_LOOKUP = AUTO
    ANGULAR_TOLERANCE_CHOICE = Automatic
    THICKNESS_TOLERANCE_CHOICE = Automatic
    -> Offsetter_3
Offsetter_3
    MODE_LOOKUP = CARTESIAN
    SHOW_ERROR_INDICATORS = No
    XOFF = -@Value(__normal_x)*@Value(__extension_distance)
    YOFF = -@Value(__normal_y)*@Value(__extension_distance)
    ZOFF = -@Value(__normal_z)*@Value(__extension_distance)
    MODE = Cartesian Coordinate
    OFFSET -> Extruder_4
Extruder_4
    DIRECTION_LOOKUP = AUTO
    DISTANCE = @Value(__extension_distance)*2
    SHOW_ERROR_INDICATORS = No
    DIRECTION = Auto
    EXTRUDED -> Junction_21

Bookmark: 開口部を前後一定距離押し出したソリッドに変換
GeometryPartExtractor_3
    GQUERY:
      for $geom in //geometry
      where $geom/@fme_geometry_type = 'IFMEFace'
      return number($geom/@fme_id)
    SHOW_ERROR_INDICATORS = No
    EXTRACTED -> GeometryValidator
GeometryValidator
    ISSUE_ATTR_NAME = _issues
    PRESETS = Custom
    REPAIR = Yes
    RULES = CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SHOW_ERROR_INDICATORS = No
    SUMMARY = Detailed
    PASSED -> GeometryFilter_2
    REPAIRED -> GeometryFilter_2
GeometryFilter_2
    FILTER_MODE = COMPLETE
    FILTER_MULTI = FILTER_TYPES]Face]FILTER_TYPES_Complete]Face]INSTANCES]INSTANCE
    FILTER_TYPES = Face
    FILTER_TYPES_Complete = Face
    INSTANCES = INSTANCE
    SHOW_ERROR_INDICATORS = No
    Face -> PlanarityFilter_3
PlanarityFilter_3
    ANGULAR_TOLERANCE = 20
    ANGULAR_TOLERANCE_CHOICE_LOOKUP = CUSTOM
    OUTPUT_LOOKUP = EXPOSE_SURFACE_NORMAL
    SHOW_ERROR_INDICATORS = No
    THICKNESS_TOLERANCE = 30
    THICKNESS_TOLERANCE_CHOICE_LOOKUP = CUSTOM
    ANGULAR_TOLERANCE_CHOICE = Custom
    OUTPUT_NORMAL = Yes
    THICKNESS_TOLERANCE_CHOICE = Custom
    PLANAR -> TestFilter_2
TestFilter_2
    DEFAULT_VALUE = <UNFILTERED>
    PASSED_TEST_GROUP_OUTPUT = FIRST
    PRESERVE_FEATURE_ORDER_LOOKUP = PER_OUTPUT_PORT
    SHOW_ERROR_INDICATORS = No
    TEST_LIST:
      "BOOL_OP,COMPOSITE,COMPOSITE_TEST,""""""1 AND 2 AND 3"""""",TEST_CLAUSE,TEST @Evaluate(@abs(@Value(_surfaceNormalX)-@Value(__normal_x))) < 0.01
      TEST @Evaluate(@abs(@Value(_surfaceNormalY)-@Value(__normal_y))) < 0.01
      TEST @Evaluate(@abs(@Value(_surfaceNormalZ)-@Value(__normal_z))) < 0.01",Side 1,"BOOL_OP,COMPOSITE,COMPOSITE_TEST,""""""1 AND 2 AND 3"""""",TEST_CLAUSE,TEST @Evaluate(@abs(-@Value(_surfaceNormalX)-@Value(__normal_x))) < 0.01
      TEST @Evaluate(@abs(-@Value(_surfaceNormalY)-@Value(__normal_y))) < 0.01
      TEST @Evaluate(@abs(-@Value(_surfaceNormalZ)-@Value(__normal_z))) < 0.01",Side 2
    Side 1 -> CenterPointExtractor
    Side 2 -> CenterPointExtractor_2
CenterPointExtractor
    CENTX = __x1
    CENTY = __y1
    CENTZ = __z1
    EXTRACTIONMODE = CENTER
    SHOW_ERROR_INDICATORS = No
    -> FeatureMerger_4 [REQUESTOR]
CenterPointExtractor_2
    CENTX = __x2
    CENTY = __y2
    CENTZ = __z2
    EXTRACTIONMODE = CENTER
    SHOW_ERROR_INDICATORS = No
    -> FeatureMerger_4 [SUPPLIER]
FeatureMerger_4
    ATTR_ACCUM_MODE = Merge Supplier
    ATTR_CONFLICT_RES_LOOKUP = REQUESTOR_IF_CONFLICT
    GROUP_BY = __opening_id fme_basename
    IGNORE_NULLS = No
    JOIN_KEYS = 1 1 AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> AttributeCreator_5
AttributeCreator_5
    ATTR_TABLE:
      SET_TO __distance (varchar(200)) = @Evaluate(@sqrt((@Value(__x2)-@Value(__x1))**2 + (@Value(__y2)-@Value(__y1))**2 + (@Value(__z2)-@Value(__z1))**2))
      SET_TO __area (buffer) = @Area(SLOPED_AREAS)
    SHOW_ERROR_INDICATORS = No
    -> Offsetter_2
Offsetter_2
    MODE_LOOKUP = CARTESIAN
    SHOW_ERROR_INDICATORS = No
    XOFF = -@Value(__normal_x)*(@Value(__extension_distance)+@Value(__distance)*0.5)
    YOFF = -@Value(__normal_y)*(@Value(__extension_distance)+@Value(__distance)*0.5)
    ZOFF = -@Value(__normal_z)*(@Value(__extension_distance)+@Value(__distance)*0.5)
    MODE = Cartesian Coordinate
    OFFSET -> Extruder
Extruder
    DIRECTION_LOOKUP = AUTO
    DISTANCE = @Value(__extension_distance)*2
    SHOW_ERROR_INDICATORS = No
    DIRECTION = Auto
    EXTRUDED -> AttributeManager_5
AttributeManager_5
    ATTR_TABLE:
      REMOVE fme_feature_type (char(50))
      REMOVE _surfaceNormalX (real64)
      REMOVE _surfaceNormalY (real64)
      REMOVE _surfaceNormalZ (real64)
      REMOVE _pointOnSurfaceX (real64)
      REMOVE _pointOnSurfaceY (real64)
      REMOVE _pointOnSurfaceZ (real64)
      REMOVE __x1 (real64)
      REMOVE __y1 (real64)
      REMOVE __z1 (real64)
      REMOVE __x2 (real64)
      REMOVE __y2 (real64)
      REMOVE __z2 (real64)
      REMOVE __distance (varchar(200))
      RENAME_SET_VALUE _zmin (real64)
      REMOVE _issues{}.count (uint32)
      REMOVE _issues{}.issue_found (buffer)
      REMOVE _issues{}.location_sample.x (real64)
      REMOVE _issues{}.location_sample.y (real64)
      REMOVE _issues{}.location_sample.z (real64)
      REMOVE __extension_distance (varchar(200))
    SHOW_ERROR_INDICATORS = No
    -> GeometryExtractor_3

Bookmark: 屋内空間境界面の開口部切り取り
Note: 水平面（天井、床）の穴あけ
Clipper_interior_horizontal
    ADD_NODATA = YES
    ATTR_ACCUM_MODE = MERGE
    ATTR_CONFLICT_RES = CLIPPER
    BOUNDARY_CASES = INSIDE
    CLEANING_TOLERANCE_LOOKUP = AUTO
    CLIPPED_ATTR = __clipped
    CLIPPERS_FIRST = NO
    GENERATE_LIST = NO
    GROUP_BY = fme_basename
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    SHOW_ERROR_INDICATORS = No
    Z_VAL_SOURCE = CANDIDATE
    CLEANING_TOLERANCE = Automatic
    MISSING_M_MODE = Linear Interpolation
    MISSING_Z_MODE = Planar Interpolation
    INSIDE -> Tester_8
    OUTSIDE -> Tester_5
Note: Clipper : Clipper / 屋外壁開口部穴あけ
Junction_41
    SHOW_ERROR_INDICATORS = No
    -> Junction_42
Note: AttributeKeeper : Input
Junction_19
    SHOW_ERROR_INDICATORS = No
    -> Junction_20
Note: 鉛直面（屋内壁の穴あけ
Clipper_interior_vertical
    ADD_NODATA = YES
    ATTR_ACCUM_MODE = MERGE
    ATTR_CONFLICT_RES = CLIPPER
    BOUNDARY_CASES = INSIDE
    CLEANING_TOLERANCE_LOOKUP = AUTO
    CLIPPED_ATTR = __clipped
    CLIPPERS_FIRST = NO
    GENERATE_LIST = NO
    GROUP_BY = _storey_index __rounded_normal_x __rounded_normal_y fme_basename
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    SHOW_ERROR_INDICATORS = No
    Z_VAL_SOURCE = CANDIDATE
    CLEANING_TOLERANCE = Automatic
    MISSING_M_MODE = Linear Interpolation
    MISSING_Z_MODE = Planar Interpolation
    INSIDE -> Tester_8
    OUTSIDE -> Tester_5

Bookmark: 「開口部あり : 鉛直の開口部に一定距離内で近接する同一 storey の壁面 (最大2面) 」と「開口部なし」に分岐
NeighborFinder
    ATTR_ACCUM_MODE = Merge Candidate
    ATTR_CONFLICT_RES_LOOKUP = ORIGINAL_IF_CONFLICT
    CANDIDATES_FIRST = No
    CLOSE_LIST_ATTRS_TO_INCLUDE_MODE_LU = ALL
    CLOSE_LIST_NAME = __found
    GROUP_BY = _storey_index fme_basename
    HAS_BASE = YES
    INSERT_VERTEX = No
    K = 2
    MAX = $(OPENING_EXTENSION_DISTANCE_V)
    MEASURES_FROM_CANDIDATE = Yes
    MEASURE_TYPE_LOOKUP = CONTINUOUS
    SHOW_ERROR_INDICATORS = No
    TREAT_POLYGON = LINE
    ATTR_CONFLICT_RES = Use Base
    CLOSE_LIST_ATTRS_TO_INCLUDE_MODE = All Attributes
    MEASURE_TYPE = Continuous
    MODE = Bases and Candidates
    TREAT_POLYGON_AS = Lines
    MATCHED -> AttributeManager_4
    UNMATCHED_CANDIDATE -> GeometryReplacer_2
AttributeManager_4
    ATTR_TABLE:
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      RENAME_SET_VALUE __found{}.distance > __found{}.__distance (real64)
      REMOVE __found{}.angle (real64)
      REMOVE __found{}.candidate_angle (real64)
      REMOVE __found{}.candidate_label_angle (real64)
      REMOVE __found{}.closest_candidate_x (real64)
      REMOVE __found{}.closest_candidate_y (real64)
      REMOVE __found{}.closest_base_x (real64)
      REMOVE __found{}.closest_base_y (real64)
    SHOW_ERROR_INDICATORS = No
    -> ListExploder
ListExploder
    ATTR_CONFLICT_RES_LOOKUP = INCOMING_IF_CONFLICT
    INDEX_ATTR = _element_index
    LIST_ATTR = __found{}
    SHOW_ERROR_INDICATORS = No
    ATTR_ACCUM_MODE = Merge List Attributes
    ATTR_CONFLICT_RES = Use List Attribute Values
    ELEMENTS -> DuplicateFilter_2
Note: 重複を除外
DuplicateFilter_2
    INPUT_ORDERED_CHOICE_LOOKUP = NO
    KEYATTR = __int_bdry_gml_id
    PRESERVE_FEATURE_ORDER_LOOKUP = PER_OUTPUT_PORT
    SHOW_ERROR_INDICATORS = No
    INPUT_ORDERED_CHOICE = No
    UNIQUE -> GeometryReplacer
Note: ジオメトリを復元
GeometryReplacer
    KIND = fmebinary
    REMOVE_ATTRIBUTE = Yes
    SHOW_ERROR_INDICATORS = No
    SOURCE = @Value(__geometry)
    KIND_LONG = FME Binary
    -> Junction_68
Note: ジオメトリを復元
GeometryReplacer_2
    KIND = fmebinary
    REMOVE_ATTRIBUTE = Yes
    SHOW_ERROR_INDICATORS = No
    SOURCE = @Value(__geometry)
    KIND_LONG = FME Binary
    -> Junction_14
Junction_14
    SHOW_ERROR_INDICATORS = No
    -> Junction_13

Bookmark: 全面がドア、窓である境界面について、ジオメトリを持たない境界面フィーチャー (Door, Window の親要素) を作成
GeometryRemover
    REMOVE_COORDSYS = No
    SHOW_ERROR_INDICATORS = No
    -> FeatureMerger_7 [REQUESTOR]
DuplicateFilter_4
    INPUT_ORDERED_CHOICE_LOOKUP = NO
    KEYATTR = __int_bdry_gml_id
    PRESERVE_FEATURE_ORDER_LOOKUP = PER_OUTPUT_PORT
    SHOW_ERROR_INDICATORS = No
    INPUT_ORDERED_CHOICE = No
    UNIQUE -> FeatureMerger_7 [SUPPLIER]
FeatureMerger_7
    ATTR_ACCUM_MODE = Merge Supplier
    ATTR_CONFLICT_RES_LOOKUP = REQUESTOR_IF_CONFLICT
    IGNORE_NULLS = No
    JOIN_KEYS = @Value(__int_bdry_gml_id) @Value(__int_bdry_gml_id) AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> AttributeManager_11
AttributeManager_11
    ATTR_TABLE:
      SET_TO _citygml_feature_type (buffer) = FME_CONDITIONAL:DEFAULT_VALUE'FloorSurface'BOOL_OP;OR;COMPOSITE_TEST;1;TEST @Evaluate(@abs(@Value(__normal_z))) < 0.1'InteriorWallSurface'BOOL_OP;OR;COMPOSITE_TEST;1;TEST 0 < @Value(__normal_z)'CeilingSurface'FME_NUM_CONDITIONS3___
      REMOVE __orientation (varchar(200))
      REMOVE __normal_x (real64)
      REMOVE __normal_y (real64)
      REMOVE __normal_z (real64)
      REMOVE __normal (varchar(200))
      REMOVE __rounded_normal_x (varchar(200))
      REMOVE __rounded_normal_y (varchar(200))
      REMOVE __opening_id (char(36))
      REMOVE ifc_parent_feature_type (buffer)
      REMOVE _zmin (real64)
      REMOVE _zmax (real64)
      REMOVE __bldg_gml_id (varchar(200))
      REMOVE __clipped (char(3))
      REMOVE __distance (real64)
      REMOVE _element_index (uint32)
    SHOW_ERROR_INDICATORS = No
    -> Junction_57

Bookmark: 隣接する屋内空間が共有している同一形状の境界面 -> ClosureSurface
Note: 開口部のなかったものとあったものに分岐
Tester_5
    BOOL_OP = OR
    PRESERVE_FEATURE_ORDER_LOOKUP = PER_OUTPUT_PORT
    SHOW_ERROR_INDICATORS = No
    TEST_CLAUSE = CASE_INSENSITIVE_TEST @Value(__clipped) = no
    TEST_MODE = CASE_INSENSITIVE_TEST
    PASSED -> Matcher
    FAILED -> Junction_10
Matcher
    BLANK_AND_MISSING_DIFFER = No
    CHECK_COORDINATE_SYSTEMS = No
    CHECK_TYPES_AND_ENCODINGS = No
    CNT_ATTR = _match_id
    LENIENT_MATCH = Yes
    MATCH = 3D
    MATCHATTRS = __bldg_gml_id fme_basename
    MATCH_STRATEGY_LOOKUP = MATCH
    SHOW_ERROR_INDICATORS = No
    MATCH_STRATEGY = Match Selected Attributes
    MATCHED -> AttributeCreator_6
    NOT_MATCHED -> AttributeCreator_7
Junction_10
    SHOW_ERROR_INDICATORS = No
    -> Junction_75
Junction_75
    SHOW_ERROR_INDICATORS = No
    -> AttributeCreator_7

Bookmark: CityGMLフィーチャータイプ名設定
Note: ClosureSurface
AttributeCreator_6
    ATTR_TABLE = SET_TO _citygml_feature_type (buffer) = ClosureSurface
    SHOW_ERROR_INDICATORS = No
    -> Junction_26
Note: InteriorWallSurface / CeilingSurface / FloorSurface
AttributeCreator_7
    ATTR_TABLE = SET_TO _citygml_feature_type (varchar(200)) = FME_CONDITIONAL:DEFAULT_VALUE'FloorSurface'BOOL_OP;OR;COMPOSITE_TEST;1;TEST @Evaluate(@abs(@Value(__normal_z))) < 0.1'InteriorWallSurface'BOOL_OP;OR;COMPOSITE_TEST;1;TEST 0 < @Value(__normal_z)'CeilingSurface'FME_NUM_CONDITIONS3___
    SHOW_ERROR_INDICATORS = No
    -> Junction_26

Bookmark: ジオリファレンスと投影変換
FeatureMerger_6
    ATTR_ACCUM_MODE = Merge Supplier
    ATTR_CONFLICT_RES_LOOKUP = REQUESTOR_IF_CONFLICT
    GROUP_BY = fme_basename
    IGNORE_NULLS = No
    JOIN_KEYS = 1 1 AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> PLATEAU4.Reprojector
PLATEAU4.Reprojector
    DEST_COORDSYS = $(DEST_COORDSYS)
    REPROJECTION_PARAMS = @Value(_reprojection_params)
    Ourput -> AttributeFilter

Bookmark: IntBuildingInstallation について関連役割属性名変更
Tester_14
    BOOL_OP = OR
    PRESERVE_FEATURE_ORDER_LOOKUP = PER_OUTPUT_PORT
    SHOW_ERROR_INDICATORS = No
    TEST_CLAUSE = TEST @Value(_citygml_feature_type) = IntBuildingInstallation
    TEST_MODE = TEST
    PASSED -> ListRenamer
    FAILED -> Junction_96
ListRenamer
    LEAVE_ORIG = No
    LIST_ACTION = Rename
    LIST_COMPONENT_NAMES = uro_ifc_building_installation_attribute{},uro_ifc_int_building_installation_attribute{}
    LIST_NAME = uro_ifc_building_installation_attribute{}
    SHOW_ERROR_INDICATORS = No
    -> Junction_96

Bookmark: CityObjectGroup 追加
XMLUpdater
    GROUP_BY = fme_basename
    OUTPUT_XML_HEADER_LOOKUP = YES
    QUERY_VALIDATE = YES
    RESULT_ATTRIBUTE = _result
    SHOW_ERROR_INDICATORS = No
    UPDATE_TABLE = GENERATE_QUERY INSERT_LAST /core:CityModel XML fme:get-xml-attribute("_xml_fragment")/*/core:cityObjectMember
    XML_FILE = @Value(_dataset)
    XML_TYPE = XML File
    OUTPUT_XML_HEADER = Yes
    VISIBLE_QUERY_VALIDATE = Yes
    DOCUMENT -> XMLFormatter
XMLFormatter
    COLLAPSE_EMPTY_ELEMENT = No
    FORMAT_MODE = PRETTY_PRINT
    INDENT_SIZE = 1
    LIST_NAME = _xml_error
    MOVE_NAMESPACE_TO_ROOT = No
    NAMESPACE_CLEANUP = Yes
    OUTPUT_ENCODING = utf-8
    PARSER_CHOICE = LIBXML2
    REMOVE_ALL_COMMENT = No
    REMOVE_DTD = No
    REMOVE_EMPTY_ELEMENT = Yes
    REMOVE_XML_HEADER = no
    REPLACE_TABS_WITH_SPACES = no
    SCHEMALOC_CLEANUP = No
    SHOW_ERROR_INDICATORS = No
    TEXT_INDENT = no
    WHITESPACE_HANDLING = Remove excess whitespace
    XML_ATTR_TEXT = _result
    XML_INPUT_TYPE = Attribute Specifying XML Text
    XML_OUTPUT_FILE_ENCODED = @Value(_dataset)
    XML_OUTPUT_TYPE = XML File
    FORMATTING_CHOICE = Pretty-Print XML

FME custom transformer SolidBoundaryCloser

Parameters:
- GRP_GROUP_PROCESSING =   # Group Processing
- FME_PROCESS_GROUP_BY =   # "" Group By (Solid ID Attribute)
- FME_PROCESS_GROUPS_ORDERED = No   # When All Features Received,No%When Group Changes (Advanced),Yes Complete Groups
- GRP_APPEARANCE_HANDLING =   # APPEARANCE_HANDLING_MODE Appearance Handling
- APPEARANCE_HANDLING_MODE = Keep   # Appearance Handling Mode

Boundary (input)
    -> Deaggregator
Deaggregator
    EXPLODE_INSTANCES = No
    LIST_ATTR_MODE_LOOKUP = LEAN
    RECURSIVE = Yes
    SHOW_ERROR_INDICATORS = No
    SPLIT_COMPOSITES = Yes
    MODE = Flatten All Levels
    DEAGGREGATED -> Counter
Note: __face_id
Counter
    CNT_ATTR = __face_id
    SCOPE = Local
    SHOW_ERROR_INDICATORS = No
    START = 0
    -> Junction_7
    -> GeometryCoercer
    -> AttributeKeeper
AttributeKeeper
    CREATE_BULK_MODE_FEATURES = NO
    KEEP_ATTRS = __face_id
    SHOW_ERROR_INDICATORS = No
    -> AppearanceExtractor
AppearanceExtractor
    ACCUM_ATTRS = Yes
    ACCUM_TRAITS = No
    GQUERY:
      for $geom in //geometry
      where $geom/count(parent::geometry) = 0
      return number($geom/@fme_id)
    SHOW_ERROR_INDICATORS = No
    SIDE_OPTION = FRONT
    UNIQUE_DEFINITIONS = NO
    SIDE_TO_EXTRACT = Front Side
    UNIQUE_STYLES = No
    APPEARANCE -> Junction_3
    UNUSED -> Junction_2
Note: AppearanceSetter : Appearance
Junction_3
    SHOW_ERROR_INDICATORS = No
    -> Junction_4
Note: AppearanceExtractor : Appearance
Junction_4
    SHOW_ERROR_INDICATORS = No
    -> AppearanceSetter [APPEARANCE]
Junction_2
    SHOW_ERROR_INDICATORS = No
Junction_7
    SHOW_ERROR_INDICATORS = No
    -> Junction_8
Junction_8
    SHOW_ERROR_INDICATORS = No
    -> FeatureMerger_2 [REQUESTOR]
GeometryCoercer
    GQUERY:
      for $geom in //geometry
      where $geom/count(parent::geometry) = 0
      return number($geom/@fme_id)
    KIND = fme_polygon
    SHOW_ERROR_INDICATORS = No
    COERCED -> DonutHoleExtractor
DonutHoleExtractor
    DEAGGREGATE_INPUT = Yes
    SHOW_ERROR_INDICATORS = No
    OUTERSHELL -> AttributeCreator
    HOLE -> Counter_2
Note: __hole_id = 0
AttributeCreator
    ATTR_TABLE = SET_TO __hole_id (uint64) = 0
    SHOW_ERROR_INDICATORS = No
    -> Sorter
Note: __hole_id = 1,2,3 ... / for each Donut
Counter_2
    CNT_ATTR = __hole_id
    GROUP_BY = __face_id
    SCOPE = Local
    SHOW_ERROR_INDICATORS = No
    START = 1
    -> Sorter
Sorter
    GROUP_BY = __face_id
    SHOW_ERROR_INDICATORS = No
    SORT_PARM = __hole_id NUMERIC ASCENDING
    SORTED -> Chopper
Chopper
    DEAGGREGATE_INPUT = Deaggregate
    MAX_VERTICES = 2
    MODE_LOOKUP = VERTEX
    REMNANT_ATTR = _remnant
    SHOW_ERROR_INDICATORS = No
    MODE = By Vertex
    CHOPPED -> Counter_3
Note: __edge_id
Counter_3
    CNT_ATTR = __edge_id
    GROUP_BY = __face_id __hole_id
    SCOPE = Local
    SHOW_ERROR_INDICATORS = No
    START = 0
    -> Matcher
Matcher
    CHECK_COORDINATE_SYSTEMS = No
    CNT_ATTR = __match_id
    LENIENT_MATCH = Yes
    MATCH = 3D
    SHOW_ERROR_INDICATORS = No
    MATCHED -> Junction_11
    NOT_MATCHED -> PythonCaller_2
    NOT_MATCHED -> DuplicateFilter
Junction_11
    SHOW_ERROR_INDICATORS = No
    -> Junction_12
Junction_12
    SHOW_ERROR_INDICATORS = No
    -> FeatureMerger [REQUESTOR]
DuplicateFilter
    INPUT_ORDERED_CHOICE_LOOKUP = NO
    KEYATTR = __face_id
    PRESERVE_FEATURE_ORDER_LOOKUP = PER_OUTPUT_PORT
    SHOW_ERROR_INDICATORS = No
    INPUT_ORDERED_CHOICE = No
    UNIQUE -> FeatureMerger_2 [SUPPLIER]
    UNIQUE -> FeatureMerger [SUPPLIER]
Note: 変更対象外の境界面抽出
FeatureMerger_2
    ATTR_ACCUM_MODE = Merge Supplier
    ATTR_CONFLICT_RES_LOOKUP = REQUESTOR_IF_CONFLICT
    IGNORE_NULLS = No
    JOIN_KEYS = @Value(__face_id) @Value(__face_id) AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    UNMERGED_REQUESTOR -> TestFileter_Appearance
TestFileter_Appearance: TestFilter
    DEFAULT_VALUE = Keep
    PASSED_TEST_GROUP_OUTPUT = FIRST
    PRESERVE_FEATURE_ORDER_LOOKUP = PER_OUTPUT_PORT
    SHOW_ERROR_INDICATORS = No
    TEST_LIST = "BOOL_OP,OR,COMPOSITE_TEST,""""""1"""""",TEST_CLAUSE,CASE_INSENSITIVE_TEST $(APPEARANCE_HANDLING_MODE) = Replace",Replace,"BOOL_OP,OR,COMPOSITE_TEST,""""""1"""""",TEST_CLAUSE,CASE_INSENSITIVE_TEST $(APPEARANCE_HANDLING_MODE) = Remove",Remove
    Remove -> AppearanceRemover_2
    Keep -> AttributeRemover
AppearanceRemover_2
    SHOW_ERROR_INDICATORS = No
    SIDE_OPTION = BOTH
    SIDE_TO_REMOVE = Front and Back Sides
    -> Junction_6
    UNMATCHED -> Junction_6
Junction_6
    SHOW_ERROR_INDICATORS = No
    -> AttributeRemover
AttributeRemover
    REMOVE_ATTRS = __face_id,_num_removed_coordinates
    SHOW_ERROR_INDICATORS = No
    -> Untouched (output)
Untouched (output)
Note: 変更対象境界面の辺のうち頂点追加がない辺を抽出
FeatureMerger
    ATTR_ACCUM_MODE = Merge Supplier
    ATTR_CONFLICT_RES_LOOKUP = REQUESTOR_IF_CONFLICT
    IGNORE_NULLS = No
    JOIN_KEYS = @Value(__face_id) @Value(__face_id) AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> Sorter_2
Note: 頂点の挿入
PythonCaller_2
    PYTHONSOURCE:
      import fme
      import fmeobjects, math

      def distance_and_unit_vector(s, e, precision):
          v = (e[0]-s[0], e[1]-s[1], e[2]-s[2])
          d = math.sqrt(v[0]**2 + v[1]**2 + v[2]**2)
          u = (round(v[0]/d,precision), round(v[1]/d,precision), round(v[2]/d,precision))
          return (d, u)

      class VertexInserter(object):
          def __init__(self):
              self.features = [] # input features
              self.vertices = set([]) # {(x,y,z)...}

          def has_support_for(self, support_type: int):
              return support_type == fmeobjects.FME_SUPPORT_FEATURE_TABLE_SHIM

          def input(self, feature: fmeobjects.FMEFeature):
              self.features.append(feature)
              self.vertices |= set(feature.getAllCoordinates())

          def close(self):
              PRECISION = 2
              for feature in self.features:
                  s = feature.getCoordinate(0)
                  e = feature.getCoordinate(1)
                  d0, u0 = distance_and_unit_vector(s, e, PRECISION)

                  vertices = [] # 挿入する頂点 (始点からの距離, (x,y,z))
                  for m in self.vertices - {s, e}:
                      d1, u1 = distance_and_unit_vector(s, m, PRECISION)
                      if u1 == u0 and d1 < d0:
                          vertices.append((d1, m))

                  if 0 < len(vertices):
                      coords = [v for _, v in sorted(vertices + [(0, s), (d0, e)])]
                      feature.setGeometry(fmeobjects.FMELine(coords))

                  self.pyoutput(feature)

          def process_group(self):
              pass
    PYTHONSYMBOL = VertexInserter
    SHOW_ERROR_INDICATORS = No
    -> Junction
Junction
    SHOW_ERROR_INDICATORS = No
    -> Sorter_2
    -> Chopper_2
Sorter_2
    SHOW_ERROR_INDICATORS = No
    SORT_PARM = __face_id NUMERIC ASCENDING __hole_id NUMERIC ASCENDING __edge_id NUMERIC ASCENDING
    SORTED -> PythonCaller_3
Note: 境界面の再構築
PythonCaller_3
    GROUP_BY = __face_id
    PYTHONSOURCE:
      import fme
      import fmeobjects


      class BoundaryFaceReplacer(object):
          def __init__(self):
              self.features = []
              self.coordList = []
              self.prevHoleId = None

          def has_support_for(self, support_type: int):
              return support_type == fmeobjects.FME_SUPPORT_FEATURE_TABLE_SHIM

          def input(self, feature: fmeobjects.FMEFeature):
              holeId = int(feature.getAttribute('__hole_id'))
              if holeId != self.prevHoleId:
                  self.features.append(feature)
                  self.coordList.append([feature.getCoordinate(0)])
                  self.prevHoleId = holeId
              self.coordList[-1] += feature.getAllCoordinates()[1:]

          def close(self):
              pass

          def process_group(self):
              feature = self.features[0]

              outer = fmeobjects.FMELine(self.coordList[0])
              if len(self.features) < 2:
                  area = fmeobjects.FMEPolygon(outer)
              else:
                  area = fmeobjects.FMEDonut(outer)
                  for i in range(1, len(self.features)):
                      area.addInnerBoundaryCurve(fmeobjects.FMELine(self.coordList[i]))

              feature.setGeometry(fmeobjects.FMEFace(area, fmeobjects.FME_CLOSE_3D_AVERAGE_MODE))
              self.pyoutput(feature)

              self.__init__()
    PYTHONSYMBOL = BoundaryFaceReplacer
    SHOW_ERROR_INDICATORS = No
    -> Tester_2
Tester_2
    BOOL_OP = OR
    PRESERVE_FEATURE_ORDER_LOOKUP = PER_OUTPUT_PORT
    SHOW_ERROR_INDICATORS = No
    TEST_CLAUSE = CASE_INSENSITIVE_TEST $(APPEARANCE_HANDLING_MODE) != Remove
    TEST_MODE = CASE_INSENSITIVE_TEST
    PASSED -> AppearanceSetter [GEOMETRY]
    FAILED -> AppearanceRemover
Note: アピアランス復元/設定
AppearanceSetter
    APPEARANCE_DEFINITION_STORAGE = CREATE
    GQUERY:
      for $geom in //geometry
      where $geom/count(parent::geometry) = 0
      return number($geom/@fme_id)
    GROUP_BY = __face_id
    INPUT_PORT_APPEARANCE_CONNECTED = CONNECTED
    INPUT_PORT_HOLDER_CONNECTED = *
    SHOW_ERROR_INDICATORS = No
    SIDE_OPTION = FRONT
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front Side
    TEXTURE_MAPPING_TYPE_CHOICE = Surface Normal
    USE_EXISTING_TEXTURE_COORDINATES = No
    -> Junction_5
AppearanceRemover
    SHOW_ERROR_INDICATORS = No
    SIDE_OPTION = BOTH
    SIDE_TO_REMOVE = Front and Back Sides
    -> Junction_5
    UNMATCHED -> Junction_5
Junction_5
    SHOW_ERROR_INDICATORS = No
    -> FeatureMerger_3 [REQUESTOR]
DuplicateFilter_2
    INPUT_ORDERED_CHOICE_LOOKUP = NO
    KEYATTR = __face_id
    PRESERVE_FEATURE_ORDER_LOOKUP = PER_OUTPUT_PORT
    SHOW_ERROR_INDICATORS = No
    INPUT_ORDERED_CHOICE = No
    UNIQUE -> FeatureMerger_3 [SUPPLIER]
Note: 修復できなかった面とできた面に分岐
FeatureMerger_3
    ATTR_ACCUM_MODE = Merge Supplier
    ATTR_CONFLICT_RES_LOOKUP = REQUESTOR_IF_CONFLICT
    IGNORE_NULLS = No
    JOIN_KEYS = @Value(__face_id) @Value(__face_id) AUTO
    MERGE_TYPE_VAL = ATTRIBUTES
    PRESERVE_FEATURE_ORDER_LOOKUP = PER_OUTPUT_PORT
    PROCESS_DUPS = NO
    REJECT_NULL_MISSING_KEYS = No
    SHOW_ERROR_INDICATORS = No
    SUPPLIERS_FIRST = No
    ATTR_CONFLICT_RES = Use Requestor
    MERGE_TYPE = Attributes Only
    MERGED -> AttributeRemover_3
    UNMERGED_REQUESTOR -> AttributeRemover_2
AttributeRemover_2
    REMOVE_ATTRS = __edge_id,__face_id,__hole_id,__match_id,_num_removed_coordinates
    SHOW_ERROR_INDICATORS = No
    -> Repaired (output)
Repaired (output)
AttributeRemover_3
    REMOVE_ATTRS = __edge_id,__face_id,__hole_id,__match_id,_num_removed_coordinates
    SHOW_ERROR_INDICATORS = No
    -> Failed (output)
Failed (output)

Bookmark: 修復できなかった辺を抽出
Chopper_2
    DEAGGREGATE_INPUT = Deaggregate
    MAX_VERTICES = 2
    MODE_LOOKUP = VERTEX
    SHOW_ERROR_INDICATORS = No
    MODE = By Vertex
    CHOPPED -> Matcher_2
    UNTOUCHED -> Matcher_2
Matcher_2
    CHECK_COORDINATE_SYSTEMS = No
    CNT_ATTR = __match_id
    LENIENT_MATCH = Yes
    MATCH = 3D
    SHOW_ERROR_INDICATORS = No
    NOT_MATCHED -> DuplicateFilter_2

Bookmark: ボツ
Note: 境界ラインのうち同一直線上にある連続した辺の間の頂点を削除した後、個別の辺（線分）に分解
PythonCaller [off]
    PYTHONSOURCE:
      import fme
      import fmeobjects, math

      def distance_and_unit_vector(s, e, precision):
          v = (e[0]-s[0], e[1]-s[1], e[2]-s[2])
          d = math.sqrt(v[0]**2 + v[1]**2 + v[2]**2)
          u = (round(v[0]/d,precision), round(v[1]/d,precision), round(v[2]/d,precision))
          return (d, u)

      class SegmentSeparator(object):
          def __init__(self):
              pass

          def has_support_for(self, support_type: int):
              return support_type == fmeobjects.FME_SUPPORT_FEATURE_TABLE_SHIM

          def input(self, feature: fmeobjects.FMEFeature):
              PRECISION = 2
              coords = feature.getAllCoordinates()
              v0 = coords[0]
              v1 = coords[1]
              _, u0 = distance_and_unit_vector(v0, v1, PRECISION)

              vertices = [v0]
              for v2 in coords[2:]:
                  _, u1 = distance_and_unit_vector(v1, v2, PRECISION)
                  if u1 != u0:
                      vertices.append(v1)
                      u0 = u1
                  v1 = v2
              vertices.append(coords[-1])

              for i in range(len(vertices) -1):
                  feature.setGeometry(fmeobjects.FMELine(vertices[i:i+2]))
                  self.pyoutput(feature)

          def close(self):
              pass

          def process_group(self):
              pass
    PYTHONSYMBOL = SegmentSeparator
    SHOW_ERROR_INDICATORS = No

FME custom transformer BrepSolidReplacer

Input (input)
    -> Deaggregator
Deaggregator
    EXPLODE_INSTANCES = Yes
    LIST_ATTR_MODE_LOOKUP = LEAN
    RECURSIVE = Yes
    SHOW_ERROR_INDICATORS = No
    SPLIT_COMPOSITES = Yes
    MODE = Flatten All Levels
    DEAGGREGATED -> GeometryFilter
GeometryFilter
    FILTER_MODE = COMPLETE
    FILTER_MULTI = FILTER_TYPES]BRepSolid Box CSGSolid Extrusion Pipe]FILTER_TYPES_Complete]BRepSolid Box CSGSolid Extrusion Pipe]INSTANCES]INSTANCE
    FILTER_TYPES = BRepSolid Box CSGSolid Extrusion Pipe
    FILTER_TYPES_Complete = BRepSolid Box CSGSolid Extrusion Pipe
    INSTANCES = INSTANCE
    SHOW_ERROR_INDICATORS = No
    BRepSolid -> GeometryValidator
    Box -> GeometryCoercer
    Extrusion -> GeometryCoercer
    Pipe -> GeometryCoercer
    CSGSolid -> CSGEvaluator
    <UNFILTERED> -> <Unfiltered> (output)
GeometryCoercer
    GQUERY:
      for $geom in //geometry
      where $geom/count(parent::geometry) = 0
      return number($geom/@fme_id)
    KIND = fme_brep_solid
    SHOW_ERROR_INDICATORS = No
    COERCED -> GeometryValidator
CSGEvaluator
    SHOW_ERROR_INDICATORS = No
    -> GeometryValidator
GeometryValidator
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SOLID_VOID_REPAIR FME_CONTROLLER_QUERY_FILE]transformers/dependencies/geometryvalidator8/SOLID_VOID_REPAIR.fme]FME_CONTROLLER_CHOICE]SOLID_VOID_REPAIR SHELL_VALIDATION FLIP_APPEARANCE_MODE]FLIP_APPEARANCES]FME_CONTROLLER_QUERY_FILE]transformers/dependencies/geometryvalidator8/SHELL_VALIDATION.fme]FME_CONTROLLER_CHOICE]SHELL_VALIDATION MISSING_TEXTURE_COORDINATES FME_CONTROLLER_QUERY_FILE]transformers/dependencies/geometryvalidator8/MISSING_TEXTURE_COORDINATES.fme]FME_CONTROLLER_CHOICE]MISSING_TEXTURE_COORDINATES SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SHOW_ERROR_INDICATORS = No
    SUMMARY = Detailed
    PASSED -> Counter
    FAILED -> Invalid (output)
    REPAIRED -> Counter
Counter
    CNT_ATTR = __temp_id
    SCOPE = Local
    SHOW_ERROR_INDICATORS = No
    START = 0
    -> GeometryPartExtractor
Note: BRepSolid に変換
GeometryCoercer_2
    GQUERY:
      for $geom in //geometry
      where $geom/count(parent::geometry) = 0
      return number($geom/@fme_id)
    KIND = fme_brep_solid
    SHOW_ERROR_INDICATORS = No
    COERCED -> GeometryValidator_2
GeometryValidator_2
    ISSUE_ATTR_NAME = _issues
    PRESETS = Custom
    REPAIR = Yes
    RULES = SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SOLID_VOID_REPAIR FME_CONTROLLER_QUERY_FILE]transformers/dependencies/geometryvalidator8/SOLID_VOID_REPAIR.fme]FME_CONTROLLER_CHOICE]SOLID_VOID_REPAIR SHELL_VALIDATION FLIP_APPEARANCE_MODE]FLIP_APPEARANCES]FME_CONTROLLER_QUERY_FILE]transformers/dependencies/geometryvalidator8/SHELL_VALIDATION.fme]FME_CONTROLLER_CHOICE]SHELL_VALIDATION MISSING_TEXTURE_COORDINATES FME_CONTROLLER_QUERY_FILE]transformers/dependencies/geometryvalidator8/MISSING_TEXTURE_COORDINATES.fme]FME_CONTROLLER_CHOICE]MISSING_TEXTURE_COORDINATES SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SHOW_ERROR_INDICATORS = No
    SUMMARY = Detailed
    PASSED -> AttributeRemover
    FAILED -> <Rejected> (output)
    REPAIRED -> AttributeRemover
AttributeRemover
    LIST_ATTRS = _issues{} _issues{}.count _issues{}.issue_found _issues{}.location_sample.x _issues{}.location_sample.y _issues{}.location_sample.z
    REMOVE_ATTRS = __temp_id
    SHOW_ERROR_INDICATORS = No
    -> Output (output)
Output (output)
<Rejected> (output)
Invalid (output)
<Unfiltered> (output)

Bookmark: MultiSurface に変換
GeometryPartExtractor
    GQUERY:
      for $geom in //geometry
      where $geom/@fme_geometry_type = 'IFMEFace'
      return number($geom/@fme_id)
    SHOW_ERROR_INDICATORS = No
    EXTRACTED -> SurfaceSplitter
SurfaceSplitter
    SHOW_ERROR_INDICATORS = No
    FRONT -> SurfaceDissolver
SurfaceDissolver
    ACCUM_INPUT_ATTRS_LOOKUP = One
    DEAGGREGATE_INPUT = Yes
    GROUP_BY = __temp_id
    MATCHING_APPS = No
    NORMAL_TOLERANCE = 0.0
    OFFSET_TOLERANCE = 0.0
    SEPARATE_SURFACES = No
    SHOW_ERROR_INDICATORS = No
    ACCUM_INPUT_ATTRS = Use Attributes From One Feature
    SURFACE -> Aggregator
Aggregator
    ACCUM_ATTRS = One
    AGGREGATE_TYPE = Homogeneous Collection (If Possible)
    GROUP_BY = __temp_id
    MODE = Geometry - Assemble One Level
    SEP = ,
    SHOW_ERROR_INDICATORS = No
    ACCUM_ATTRS_NAME = Use Attributes From One Feature
    AGGREGATE -> GeometryCoercer_2

FME custom transformer XMLDeepCleaner
Removes all empty elements from an XML text specified through the XML Attribute parameter.  
A similar function is provided by XMLFormatter (set "Yes" to the "Remove Empty Elements" parameter), but this transformer ignores XML attributes and comments to determine if an XML element is empty, so the result may be different from XMLFormatter.
Example
Source XML Text
<root>
    <a>
        <b></b>
        <!-- empty but has a comment -->
    </a>
    <a>
        <b>value</b>
        <!-- has a value -->
    </a>
    <a attr="1">
        <b></b>
        <!-- empty but parent has an attribute -->
    </a>
    <a>
        <b attr="2"></b>
        <!-- empty but has an attribute -->
    </a>
</root>
XMLFormatter (Remove Empty Elements : Yes)
<root>
    <a>
        <!-- empty but has a comment -->
    </a>
    <a>
        <b>value</b>
        <!-- has a value -->
    </a>
    <a attr="1">
        <!-- empty but parent has an attribute -->
    </a>
    <a>
        <b attr="2"/>
        <!-- empty but has an attribute -->
    </a>
</root>
XMLDeepCleaner
<root>
    <a>
        <b>value</b>
        <!-- has a value -->
    </a>
</root>

Parameters:
- XML_ATTRIBUTE =   # XML Attribute
- KEEP_ROOT = Yes   # Keep Root Element,Yes%Make Result Missing,No If All Elements are Empty
- FORMATTING_CHOICE = None   # XML"%"Linearize XML" Formatting Type
- REMOVE_ALL_COMMENT = Yes   # Remove All Comments
- REMOVE_XML_HEADER = no   # Remove XML Header
- XML_OUTPUT_ATTR =   # Attribute to contain XML output

Input (input)
    -> Counter
Counter
    CNT_ATTR = __index
    SCOPE = Local
    SHOW_ERROR_INDICATORS = No
    START = 0
    -> Tester_2
    -> AttributeKeeper
Tester_2
    BOOL_OP = OR
    PRESERVE_FEATURE_ORDER_LOOKUP = PER_OUTPUT_PORT
    SHOW_ERROR_INDICATORS = No
    TEST_CLAUSE = TEST $(KEEP_ROOT) = Yes
    TEST_MODE = TEST
    PASSED -> XMLUpdater [DOCUMENT]
    FAILED -> XMLUpdater_2 [DOCUMENT]
AttributeKeeper
    CREATE_BULK_MODE_FEATURES = NO
    KEEP_ATTRS = __index
    SHOW_ERROR_INDICATORS = No
    -> XMLUpdater [UPDATE]
    -> XMLUpdater_2 [UPDATE]
XMLUpdater
    GROUP_BY = __index
    OUTPUT_XML_HEADER_LOOKUP = NO
    QUERY_VALIDATE = YES
    RESULT_ATTRIBUTE = __attribute
    SHOW_ERROR_INDICATORS = No
    UPDATE_TABLE = GENERATE_QUERY DELETE for $x in /*//* where not(normalize-space(data($x))) return $x <Unused> <Unused>
    XML_TEXT = $(XML_ATTRIBUTE)
    XML_TYPE = Text or Attribute
    OUTPUT_XML_HEADER = No
    VISIBLE_QUERY_VALIDATE = Yes
    DOCUMENT -> AttributeRemover
XMLUpdater_2
    GROUP_BY = __index
    OUTPUT_XML_HEADER_LOOKUP = NO
    QUERY_VALIDATE = YES
    RESULT_ATTRIBUTE = __attribute
    SHOW_ERROR_INDICATORS = No
    UPDATE_TABLE = GENERATE_QUERY DELETE for $x in //* where not(normalize-space(data($x))) return $x <Unused> <Unused>
    XML_TEXT = $(XML_ATTRIBUTE)
    XML_TYPE = Text or Attribute
    OUTPUT_XML_HEADER = No
    VISIBLE_QUERY_VALIDATE = Yes
    DOCUMENT -> AttributeRemover
AttributeRemover
    REMOVE_ATTRS = __index
    SHOW_ERROR_INDICATORS = No
    -> Tester
Tester
    BOOL_OP = OR
    PRESERVE_FEATURE_ORDER_LOOKUP = PER_OUTPUT_PORT
    SHOW_ERROR_INDICATORS = No
    TEST_CLAUSE = TEST __attribute NOT_ATTRIBUTE_HAS_A_VALUE ""
    TEST_MODE = TEST
    PASSED -> AttributeRemover_2
    FAILED -> XMLFormatter
XMLFormatter
    COLLAPSE_EMPTY_ELEMENT = No
    FORMAT_MODE = $(FORMATTING_CHOICE)
    INDENT_SIZE = 1
    LIST_NAME = _xml_error
    MOVE_NAMESPACE_TO_ROOT = No
    NAMESPACE_CLEANUP = Yes
    OUTPUT_ENCODING = utf-8
    PARSER_CHOICE = LIBXML2
    REMOVE_ALL_COMMENT = $(REMOVE_ALL_COMMENT)
    REMOVE_DTD = No
    REMOVE_EMPTY_ELEMENT = No
    REMOVE_XML_HEADER = $(REMOVE_XML_HEADER)
    REPLACE_TABS_WITH_SPACES = no
    SCHEMALOC_CLEANUP = No
    SHOW_ERROR_INDICATORS = No
    TEXT_INDENT = no
    WHITESPACE_HANDLING = Remove excess whitespace
    XML_ATTR_TEXT = __attribute
    XML_INPUT_TYPE = Attribute Specifying XML Text
    XML_OUTPUT_ATTR = $(XML_OUTPUT_ATTR)
    XML_OUTPUT_TYPE = Attribute
    FORMATTING_CHOICE = $(FORMATTING_CHOICE)
    PASSED -> AttributeRemover_2
    FAILED -> AttributeRemover_3
AttributeRemover_2
    REMOVE_ATTRS = __attribute
    SHOW_ERROR_INDICATORS = No
    -> Output (output)
Output (output)
AttributeRemover_3
    REMOVE_ATTRS = __attribute
    SHOW_ERROR_INDICATORS = No
    -> <Rejected> (output)
<Rejected> (output)

FME custom transformer PLATEAU4.Reprojector

Parameters:
- REPROJECTION_PARAMS =   # Reprojection Parameters (JSON)
- DEST_COORDSYS = EPSG:6697   # Destination Coordinate System

Input (input)
    -> JSONFlattener
JSONFlattener
    ERROR_LIST_ATTR = _json_error
    JSON_DOCUMENT = $(REPROJECTION_PARAMS)
    PREFIX_STRING = __
    READ_FROM_FILE = NO
    RECURSIVE_LOOKUP = YES
    SHOW_ERROR_INDICATORS = No
    RECURSIVE = Yes
    -> AttributeExposer
    <REJECTED> -> Ourput (output)
AttributeExposer
    ATTR_TABLE = __MapConversion.Eastings,,__MapConversion.Northings,,__MapConversion.OrthogonalHeight,,__MapConversion.Scale,,__MapConversion.XAxisAbscissa,,__MapConversion.XAxisOrdinate,,__ProjectedCRS.Description,,__ProjectedCRS.GeodeticDatum,,__ProjectedCRS.MapProjection,,__ProjectedCRS.MapZone,,__ProjectedCRS.Name,,__ProjectedCRS.VerticalDatum,
    SHOW_ERROR_INDICATORS = No
    -> GeometryFilter
GeometryFilter
    FILTER_MODE = SIMPLE
    FILTER_MULTI = FILTER_TYPES]Null]FILTER_TYPES_Simple]Null
    FILTER_TYPES = Null
    FILTER_TYPES_Simple = Null
    SHOW_ERROR_INDICATORS = No
    Null -> Tester_3
    <UNFILTERED> -> Tester
Tester
    BOOL_OP = OR
    PRESERVE_FEATURE_ORDER_LOOKUP = PER_OUTPUT_PORT
    SHOW_ERROR_INDICATORS = No
    TEST_CLAUSE = TEST $(REPROJECTION_PARAMS) TYPE JSON
    TEST_MODE = TEST
    PASSED -> 3DRotator
    FAILED -> Scaler_3
Scaler_3
    DISABLE_FACTORIES = __DISABLED__
    RASTER_SCALING = Extents
    SHOW_ERROR_INDICATORS = No
    TEXT_LOC_ONLY = Location and Size
    XSCALE = 0.001
    YSCALE = 0.001
    ZSCALE = 0.001
    SCALE_ORIGIN = 0,0
    SCALED -> Junction_5
Junction_5
    SHOW_ERROR_INDICATORS = No
    -> Junction_6
Junction_6
    SHOW_ERROR_INDICATORS = No
    -> CoordinateSystemRemover
Tester_3
    BOOL_OP = OR
    PRESERVE_FEATURE_ORDER_LOOKUP = PER_OUTPUT_PORT
    SHOW_ERROR_INDICATORS = No
    TEST_CLAUSE = TEST $(REPROJECTION_PARAMS) TYPE JSON
    TEST_MODE = TEST
    PASSED -> Junction
    FAILED -> Junction_3
Junction
    SHOW_ERROR_INDICATORS = No
    -> Junction_2
Junction_2
    SHOW_ERROR_INDICATORS = No
    -> Tester_2
Tester_2
    BOOL_OP = OR
    PRESERVE_FEATURE_ORDER_LOOKUP = PER_OUTPUT_PORT
    SHOW_ERROR_INDICATORS = No
    TEST_CLAUSE = TEST $(DEST_COORDSYS) != ""
    TEST_MODE = TEST
    PASSED -> PROJReprojector
    FAILED -> CoordinateSystemSetter
PROJReprojector
    DEST = $(DEST_COORDSYS)
    INTERPOLATION_TYPE = ,NearestNeighbor
    RASTER_CELL_SIZE_LOOKUP = ,PreserveCells
    RASTER_TOLERANCE = 0.0
    SHOW_ERROR_INDICATORS = No
    SOURCE = @Value(__ProjectedCRS.Name)
    TRANSFORM_TYPE = Automatic Transformation
    INTERPOLATION_TYPE_NAME = Nearest Neighbor
    RASTER_CELL_SIZE = Preserve Cells
    REPROJECTED -> AttributeRemover
CoordinateSystemSetter
    COORDSYS = @Value(__ProjectedCRS.Name)
    SHOW_ERROR_INDICATORS = No
    -> AttributeRemover
Junction_3
    SHOW_ERROR_INDICATORS = No
    -> Junction_4
Junction_4
    SHOW_ERROR_INDICATORS = No
    -> CoordinateSystemRemover
CoordinateSystemRemover
    SHOW_ERROR_INDICATORS = No
    -> AttributeRemover
AttributeRemover
    LIST_ATTRS = _json_error{} _json_error{}.column _json_error{}.line _json_error{}.message _json_error{}.severity
    REMOVE_ATTRS = __MapConversion.Eastings,__MapConversion.Northings,__MapConversion.OrthogonalHeight,__MapConversion.Scale,__MapConversion.XAxisAbscissa,__MapConversion.XAxisOrdinate,__ProjectedCRS.Description,__ProjectedCRS.GeodeticDatum,__ProjectedCRS.MapProjection,__ProjectedCRS.MapZone,__ProjectedCRS.Name,__ProjectedCRS.VerticalDatum,fme_rejection_code
    SHOW_ERROR_INDICATORS = No
    -> Ourput (output)
Ourput (output)

Bookmark: 投影変換パラメーターに基づくジオリファレンス
3DRotator
    ANGLE = @radToDeg(@atan2(@Value(__MapConversion.XAxisAbscissa),@Value(__MapConversion.XAxisOrdinate)))
    AXIS_CHOICE_LOOKUP = Z
    SHOW_ERROR_INDICATORS = No
    AXIS_CHOICE = Z Axis
    ROTATED -> Scaler
Scaler
    DISABLE_FACTORIES = __DISABLED__
    RASTER_SCALING = Extents
    SHOW_ERROR_INDICATORS = No
    TEXT_LOC_ONLY = Location and Size
    XSCALE = @Value(__MapConversion.Scale)
    YSCALE = @Value(__MapConversion.Scale)
    ZSCALE = @Value(__MapConversion.Scale)
    SCALE_ORIGIN = 0,0
    SCALED -> Offsetter
Offsetter
    MODE_LOOKUP = CARTESIAN
    SHOW_ERROR_INDICATORS = No
    XOFF = @Value(__MapConversion.Eastings)
    YOFF = @Value(__MapConversion.Northings)
    ZOFF = @Value(__MapConversion.OrthogonalHeight)
    MODE = Cartesian Coordinate
    OFFSET -> Scaler_2
Scaler_2
    DISABLE_FACTORIES = __DISABLED__
    RASTER_SCALING = Extents
    SHOW_ERROR_INDICATORS = No
    TEXT_LOC_ONLY = Location and Size
    XSCALE = 0.001
    YSCALE = 0.001
    ZSCALE = 0.001
    SCALE_ORIGIN = 0,0
    SCALED -> Tester_2

FME custom transformer GroupMatcher_2

Parameters:
- GROUP_PROCESSING_GROUP = NO   # Group Processing
- FME_PROCESS_GROUP_BY =   # "" Group By
- FME_PROCESS_GROUPS_ORDERED = No   # When All Features Received,No%When Group Changes (Advanced),Yes Complete Groups
- GEOM_MATCH_GROUP =   # Check Geometry
- MATCH = FULL   # Match Geometry
- BLANK_AND_MISSING_NAMES_TRAITS_DIFFER = No   # Differentiate Empty, Missing, and Null Traits
- LENIENT_MATCH = No   # Lenient Geometry Matching
- CHECK_COORDINATE_SYSTEMS = No   # Check Coordinate Systems
- VECTOR_TOLERANCE = 0   # Vector Tolerance
- OUTPUT_ATTRIBUTE_NAME_GROUP =   # Output Attribute Name
- CNT_ATTR = _match_id   # Match ID
- SM_COUNT_ATTR =   # Match Count Attribute on SingleMatched
- GENERATE_LIST_GROUP =   # Generate List
- SM_LIST_NAME =   # List Name on SingleMatched Output
- LIST_ATTRS_TO_INCLUDE_MODE = Selected Attributes   # "All Attributes"%"Selected Attributes" Add To List
- LIST_ATTRS_TO_INCLUDE =   # NO_EXPAND_LIST Selected Attributes

Input (input)
    -> Matcher
Matcher
    BLANK_AND_MISSING_NAMES_TRAITS_DIFFER = $(BLANK_AND_MISSING_NAMES_TRAITS_DIFFER)
    CHECK_COORDINATE_SYSTEMS = $(CHECK_COORDINATE_SYSTEMS)
    CNT_ATTR = $(CNT_ATTR)
    LENIENT_MATCH = $(LENIENT_MATCH)
    LIST_ATTRS_TO_INCLUDE = $(LIST_ATTRS_TO_INCLUDE)
    MATCH = $(MATCH)
    SHOW_ERROR_INDICATORS = No
    SM_COUNT_ATTR = $(SM_COUNT_ATTR)
    SM_LIST_NAME = $(SM_LIST_NAME)
    MATCHED -> Matched (output)
    SINGLE_MATCHED -> SingleMatched (output)
    NOT_MATCHED -> NotMatched (output)
Matched (output)
SingleMatched (output)
NotMatched (output)
